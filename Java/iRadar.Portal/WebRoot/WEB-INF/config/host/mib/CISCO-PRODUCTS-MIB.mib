-- MIB file created 17-Nov-2011 06:16:39, by
--   SMICng version 2.2.11-beta(PRO)(Solaris), January 20, 2001. Enterprise key cisco.com

CISCO-PRODUCTS-MIB DEFINITIONS ::= BEGIN

-- From file: "CISCO-PRODUCTS-MIB.my"
-- Compile options "4 7 F H N W 03 06 0B 0G 0N 0T"

IMPORTS
    ciscoModules, ciscoProducts
            FROM CISCO-SMI;

ciscoProductsMIB OBJECT IDENTIFIER ::= { ciscoModules 2 }
-- MODULE-IDENTITY
--  LastUpdated
--    201105100000Z
--  OrgName
--    Cisco Systems, Inc.
--  ContactInfo
--           Cisco Systems
--     Customer Service
--    
--    Postal: 170 W Tasman Drive
--     San Jose, CA  95134
--     USA
--    
--       Tel: +1 800 553-NETS
--    
--    E-mail: cs-snmp@cisco.com
--  Descr
--    This module defines the object identifiers that are
--    assigned to various hardware platforms, and hence are
--    returned as values for sysObjectID
--  RevDate
--    201105100000Z
--  RevDescr
--    Added new oids
--  RevDate
--    200505051930Z
--  RevDescr
--    Added following OIDs:
--    ciscoMPX, ciscoNMCUEEC, ciscoWLSE1132, 
--    ciscoME6340ACA, ciscoME6340DCA,
--    ciscoME6340DCA, catalyst296024TT,
--    catalyst296048TT
--  RevDate
--    200504201930Z
--  RevDescr
--    Removed DNP of catalyst6kGateway
--  RevDate
--    200504181930Z
--  RevDescr
--    Added following OIDs:
--    ciscoNme16Es1GeNoPwr, ciscoNmeX24Es1GeNoPwr,
--    ciscoNmeXd24Es2StNoPwr, ciscoNmeXd48Es2GeNoPwr,
--    catalyst6kMsfc2a, ciscoEDI, ciscoCe611K9,
--    ciscoWLSEs20.
--  RevDate
--    200204051400Z
--  RevDescr
--    CANA Assignments.
--  RevDate
--    9505310000Z
--  RevDescr
--    Miscellaneous updates.

ciscoGatewayServer OBJECT IDENTIFIER ::= { ciscoProducts 1 }
ciscoTerminalServer OBJECT IDENTIFIER ::= { ciscoProducts 2 }
ciscoTrouter    OBJECT IDENTIFIER ::= { ciscoProducts 3 }
ciscoProtocolTranslator OBJECT IDENTIFIER ::= { ciscoProducts 4 }
ciscoIGS        OBJECT IDENTIFIER ::= { ciscoProducts 5 }
cisco3000       OBJECT IDENTIFIER ::= { ciscoProducts 6 }
cisco4000       OBJECT IDENTIFIER ::= { ciscoProducts 7 }
cisco7000       OBJECT IDENTIFIER ::= { ciscoProducts 8 }
ciscoCS500      OBJECT IDENTIFIER ::= { ciscoProducts 9 }
cisco2000       OBJECT IDENTIFIER ::= { ciscoProducts 10 }
ciscoAGSplus    OBJECT IDENTIFIER ::= { ciscoProducts 11 }
cisco7010       OBJECT IDENTIFIER ::= { ciscoProducts 12 }
cisco2500       OBJECT IDENTIFIER ::= { ciscoProducts 13 }
cisco4500       OBJECT IDENTIFIER ::= { ciscoProducts 14 }
cisco2102       OBJECT IDENTIFIER ::= { ciscoProducts 15 }
cisco2202       OBJECT IDENTIFIER ::= { ciscoProducts 16 }
cisco2501       OBJECT IDENTIFIER ::= { ciscoProducts 17 }
cisco2502       OBJECT IDENTIFIER ::= { ciscoProducts 18 }
cisco2503       OBJECT IDENTIFIER ::= { ciscoProducts 19 }
cisco2504       OBJECT IDENTIFIER ::= { ciscoProducts 20 }
cisco2505       OBJECT IDENTIFIER ::= { ciscoProducts 21 }
cisco2506       OBJECT IDENTIFIER ::= { ciscoProducts 22 }
cisco2507       OBJECT IDENTIFIER ::= { ciscoProducts 23 }
cisco2508       OBJECT IDENTIFIER ::= { ciscoProducts 24 }
cisco2509       OBJECT IDENTIFIER ::= { ciscoProducts 25 }
cisco2510       OBJECT IDENTIFIER ::= { ciscoProducts 26 }
cisco2511       OBJECT IDENTIFIER ::= { ciscoProducts 27 }
cisco2512       OBJECT IDENTIFIER ::= { ciscoProducts 28 }
cisco2513       OBJECT IDENTIFIER ::= { ciscoProducts 29 }
cisco2514       OBJECT IDENTIFIER ::= { ciscoProducts 30 }
cisco2515       OBJECT IDENTIFIER ::= { ciscoProducts 31 }
cisco3101       OBJECT IDENTIFIER ::= { ciscoProducts 32 }
cisco3102       OBJECT IDENTIFIER ::= { ciscoProducts 33 }
cisco3103       OBJECT IDENTIFIER ::= { ciscoProducts 34 }
cisco3104       OBJECT IDENTIFIER ::= { ciscoProducts 35 }
cisco3202       OBJECT IDENTIFIER ::= { ciscoProducts 36 }
cisco3204       OBJECT IDENTIFIER ::= { ciscoProducts 37 }
ciscoAccessProRC OBJECT IDENTIFIER ::= { ciscoProducts 38 }
ciscoAccessProEC OBJECT IDENTIFIER ::= { ciscoProducts 39 }
cisco1000       OBJECT IDENTIFIER ::= { ciscoProducts 40 }
cisco1003       OBJECT IDENTIFIER ::= { ciscoProducts 41 }
cisco2516       OBJECT IDENTIFIER ::= { ciscoProducts 42 }
cisco1020       OBJECT IDENTIFIER ::= { ciscoProducts 43 }
cisco1004       OBJECT IDENTIFIER ::= { ciscoProducts 44 }
cisco7507       OBJECT IDENTIFIER ::= { ciscoProducts 45 }
cisco7513       OBJECT IDENTIFIER ::= { ciscoProducts 46 }
cisco7506       OBJECT IDENTIFIER ::= { ciscoProducts 47 }
cisco7505       OBJECT IDENTIFIER ::= { ciscoProducts 48 }
cisco1005       OBJECT IDENTIFIER ::= { ciscoProducts 49 }
cisco4700       OBJECT IDENTIFIER ::= { ciscoProducts 50 }
ciscoPro1003    OBJECT IDENTIFIER ::= { ciscoProducts 51 }
ciscoPro1004    OBJECT IDENTIFIER ::= { ciscoProducts 52 }
ciscoPro1005    OBJECT IDENTIFIER ::= { ciscoProducts 53 }
ciscoPro1020    OBJECT IDENTIFIER ::= { ciscoProducts 54 }
ciscoPro2500PCE OBJECT IDENTIFIER ::= { ciscoProducts 55 }
ciscoPro2501    OBJECT IDENTIFIER ::= { ciscoProducts 56 }
ciscoPro2503    OBJECT IDENTIFIER ::= { ciscoProducts 57 }
ciscoPro2505    OBJECT IDENTIFIER ::= { ciscoProducts 58 }
ciscoPro2507    OBJECT IDENTIFIER ::= { ciscoProducts 59 }
ciscoPro2509    OBJECT IDENTIFIER ::= { ciscoProducts 60 }
ciscoPro2511    OBJECT IDENTIFIER ::= { ciscoProducts 61 }
ciscoPro2514    OBJECT IDENTIFIER ::= { ciscoProducts 62 }
ciscoPro2516    OBJECT IDENTIFIER ::= { ciscoProducts 63 }
ciscoPro2519    OBJECT IDENTIFIER ::= { ciscoProducts 64 }
ciscoPro2521    OBJECT IDENTIFIER ::= { ciscoProducts 65 }
ciscoPro4500    OBJECT IDENTIFIER ::= { ciscoProducts 66 }
cisco2517       OBJECT IDENTIFIER ::= { ciscoProducts 67 }
cisco2518       OBJECT IDENTIFIER ::= { ciscoProducts 68 }
cisco2519       OBJECT IDENTIFIER ::= { ciscoProducts 69 }
cisco2520       OBJECT IDENTIFIER ::= { ciscoProducts 70 }
cisco2521       OBJECT IDENTIFIER ::= { ciscoProducts 71 }
cisco2522       OBJECT IDENTIFIER ::= { ciscoProducts 72 }
cisco2523       OBJECT IDENTIFIER ::= { ciscoProducts 73 }
cisco2524       OBJECT IDENTIFIER ::= { ciscoProducts 74 }
cisco2525       OBJECT IDENTIFIER ::= { ciscoProducts 75 }
ciscoPro751     OBJECT IDENTIFIER ::= { ciscoProducts 76 }
ciscoPro752     OBJECT IDENTIFIER ::= { ciscoProducts 77 }
ciscoPro753     OBJECT IDENTIFIER ::= { ciscoProducts 78 }
cisco751        OBJECT IDENTIFIER ::= { ciscoProducts 81 }
cisco752        OBJECT IDENTIFIER ::= { ciscoProducts 82 }
cisco753        OBJECT IDENTIFIER ::= { ciscoProducts 83 }
ciscoPro741     OBJECT IDENTIFIER ::= { ciscoProducts 84 }
ciscoPro742     OBJECT IDENTIFIER ::= { ciscoProducts 85 }
ciscoPro743     OBJECT IDENTIFIER ::= { ciscoProducts 86 }
ciscoPro744     OBJECT IDENTIFIER ::= { ciscoProducts 87 }
ciscoPro761     OBJECT IDENTIFIER ::= { ciscoProducts 88 }
ciscoPro762     OBJECT IDENTIFIER ::= { ciscoProducts 89 }
ciscoPro765     OBJECT IDENTIFIER ::= { ciscoProducts 92 }
ciscoPro766     OBJECT IDENTIFIER ::= { ciscoProducts 93 }
cisco741        OBJECT IDENTIFIER ::= { ciscoProducts 94 }
cisco742        OBJECT IDENTIFIER ::= { ciscoProducts 95 }
cisco743        OBJECT IDENTIFIER ::= { ciscoProducts 96 }
cisco744        OBJECT IDENTIFIER ::= { ciscoProducts 97 }
cisco761        OBJECT IDENTIFIER ::= { ciscoProducts 98 }
cisco762        OBJECT IDENTIFIER ::= { ciscoProducts 99 }
cisco765        OBJECT IDENTIFIER ::= { ciscoProducts 102 }
cisco766        OBJECT IDENTIFIER ::= { ciscoProducts 103 }
ciscoPro2520    OBJECT IDENTIFIER ::= { ciscoProducts 104 }
ciscoPro2522    OBJECT IDENTIFIER ::= { ciscoProducts 105 }
ciscoPro2524    OBJECT IDENTIFIER ::= { ciscoProducts 106 }
ciscoLS1010     OBJECT IDENTIFIER ::= { ciscoProducts 107 }
cisco7206       OBJECT IDENTIFIER ::= { ciscoProducts 108 }
ciscoAS5200     OBJECT IDENTIFIER ::= { ciscoProducts 109 }
cisco3640       OBJECT IDENTIFIER ::= { ciscoProducts 110 }
ciscoCatalyst3500 OBJECT IDENTIFIER ::= { ciscoProducts 111 }
ciscoWSX3011    OBJECT IDENTIFIER ::= { ciscoProducts 112 }
cisco1601       OBJECT IDENTIFIER ::= { ciscoProducts 113 }
cisco1602       OBJECT IDENTIFIER ::= { ciscoProducts 114 }
cisco1603       OBJECT IDENTIFIER ::= { ciscoProducts 115 }
cisco1604       OBJECT IDENTIFIER ::= { ciscoProducts 116 }
ciscoPro1601    OBJECT IDENTIFIER ::= { ciscoProducts 117 }
ciscoPro1602    OBJECT IDENTIFIER ::= { ciscoProducts 118 }
ciscoPro1603    OBJECT IDENTIFIER ::= { ciscoProducts 119 }
ciscoPro1604    OBJECT IDENTIFIER ::= { ciscoProducts 120 }
cisco3620       OBJECT IDENTIFIER ::= { ciscoProducts 122 }
ciscoPro3620    OBJECT IDENTIFIER ::= { ciscoProducts 123 }
ciscoPro3640    OBJECT IDENTIFIER ::= { ciscoProducts 124 }
cisco7204       OBJECT IDENTIFIER ::= { ciscoProducts 125 }
cisco771        OBJECT IDENTIFIER ::= { ciscoProducts 126 }
cisco772        OBJECT IDENTIFIER ::= { ciscoProducts 127 }
cisco775        OBJECT IDENTIFIER ::= { ciscoProducts 128 }
cisco776        OBJECT IDENTIFIER ::= { ciscoProducts 129 }
ciscoPro2502    OBJECT IDENTIFIER ::= { ciscoProducts 130 }
ciscoPro2504    OBJECT IDENTIFIER ::= { ciscoProducts 131 }
ciscoPro2506    OBJECT IDENTIFIER ::= { ciscoProducts 132 }
ciscoPro2508    OBJECT IDENTIFIER ::= { ciscoProducts 133 }
ciscoPro2510    OBJECT IDENTIFIER ::= { ciscoProducts 134 }
ciscoPro2512    OBJECT IDENTIFIER ::= { ciscoProducts 135 }
ciscoPro2513    OBJECT IDENTIFIER ::= { ciscoProducts 136 }
ciscoPro2515    OBJECT IDENTIFIER ::= { ciscoProducts 137 }
ciscoPro2517    OBJECT IDENTIFIER ::= { ciscoProducts 138 }
ciscoPro2518    OBJECT IDENTIFIER ::= { ciscoProducts 139 }
ciscoPro2523    OBJECT IDENTIFIER ::= { ciscoProducts 140 }
ciscoPro2525    OBJECT IDENTIFIER ::= { ciscoProducts 141 }
ciscoPro4700    OBJECT IDENTIFIER ::= { ciscoProducts 142 }
ciscoPro316T    OBJECT IDENTIFIER ::= { ciscoProducts 147 }
ciscoPro316C    OBJECT IDENTIFIER ::= { ciscoProducts 148 }
ciscoPro3116    OBJECT IDENTIFIER ::= { ciscoProducts 149 }
catalyst116T    OBJECT IDENTIFIER ::= { ciscoProducts 150 }
catalyst116C    OBJECT IDENTIFIER ::= { ciscoProducts 151 }
catalyst1116    OBJECT IDENTIFIER ::= { ciscoProducts 152 }
ciscoAS2509RJ   OBJECT IDENTIFIER ::= { ciscoProducts 153 }
ciscoAS2511RJ   OBJECT IDENTIFIER ::= { ciscoProducts 154 }
ciscoMC3810     OBJECT IDENTIFIER ::= { ciscoProducts 157 }
cisco1503       OBJECT IDENTIFIER ::= { ciscoProducts 160 }
cisco1502       OBJECT IDENTIFIER ::= { ciscoProducts 161 }
ciscoAS5300     OBJECT IDENTIFIER ::= { ciscoProducts 162 }
ciscoLS1015     OBJECT IDENTIFIER ::= { ciscoProducts 164 }
cisco2501FRADFX OBJECT IDENTIFIER ::= { ciscoProducts 165 }
cisco2501LANFRADFX OBJECT IDENTIFIER ::= { ciscoProducts 166 }
cisco2502LANFRADFX OBJECT IDENTIFIER ::= { ciscoProducts 167 }
ciscoWSX5302    OBJECT IDENTIFIER ::= { ciscoProducts 168 }
ciscoFastHub216T OBJECT IDENTIFIER ::= { ciscoProducts 169 }
catalyst2908xl  OBJECT IDENTIFIER ::= { ciscoProducts 170 }
catalyst2916m-xl OBJECT IDENTIFIER ::= { ciscoProducts 171 }
cisco1605       OBJECT IDENTIFIER ::= { ciscoProducts 172 }
cisco12012      OBJECT IDENTIFIER ::= { ciscoProducts 173 }
catalyst1912C   OBJECT IDENTIFIER ::= { ciscoProducts 175 }
ciscoMicroWebServer2 OBJECT IDENTIFIER ::= { ciscoProducts 176 }
ciscoFastHubBMMTX OBJECT IDENTIFIER ::= { ciscoProducts 177 }
ciscoFastHubBMMFX OBJECT IDENTIFIER ::= { ciscoProducts 178 }
ciscoUBR7246    OBJECT IDENTIFIER ::= { ciscoProducts 179 }
cisco6400       OBJECT IDENTIFIER ::= { ciscoProducts 180 }
cisco12004      OBJECT IDENTIFIER ::= { ciscoProducts 181 }
cisco12008      OBJECT IDENTIFIER ::= { ciscoProducts 182 }
catalyst2924XL  OBJECT IDENTIFIER ::= { ciscoProducts 183 }
catalyst2924CXL OBJECT IDENTIFIER ::= { ciscoProducts 184 }
cisco2610       OBJECT IDENTIFIER ::= { ciscoProducts 185 }
cisco2611       OBJECT IDENTIFIER ::= { ciscoProducts 186 }
cisco2612       OBJECT IDENTIFIER ::= { ciscoProducts 187 }
ciscoAS5800     OBJECT IDENTIFIER ::= { ciscoProducts 188 }
ciscoSC3640     OBJECT IDENTIFIER ::= { ciscoProducts 189 }
cisco8510       OBJECT IDENTIFIER ::= { ciscoProducts 190 }
ciscoUBR904     OBJECT IDENTIFIER ::= { ciscoProducts 191 }
cisco6200       OBJECT IDENTIFIER ::= { ciscoProducts 192 }
cisco7202       OBJECT IDENTIFIER ::= { ciscoProducts 194 }
cisco2613       OBJECT IDENTIFIER ::= { ciscoProducts 195 }
cisco8515       OBJECT IDENTIFIER ::= { ciscoProducts 196 }
catalyst9006    OBJECT IDENTIFIER ::= { ciscoProducts 197 }
catalyst9009    OBJECT IDENTIFIER ::= { ciscoProducts 198 }
ciscoRPM        OBJECT IDENTIFIER ::= { ciscoProducts 199 }
cisco1710       OBJECT IDENTIFIER ::= { ciscoProducts 200 }
cisco1720       OBJECT IDENTIFIER ::= { ciscoProducts 201 }
catalyst8540msr OBJECT IDENTIFIER ::= { ciscoProducts 202 }
catalyst8540csr OBJECT IDENTIFIER ::= { ciscoProducts 203 }
cisco7576       OBJECT IDENTIFIER ::= { ciscoProducts 204 }
cisco3660       OBJECT IDENTIFIER ::= { ciscoProducts 205 }
cisco1401       OBJECT IDENTIFIER ::= { ciscoProducts 206 }
cisco2620       OBJECT IDENTIFIER ::= { ciscoProducts 208 }
cisco2621       OBJECT IDENTIFIER ::= { ciscoProducts 209 }
ciscoUBR7223    OBJECT IDENTIFIER ::= { ciscoProducts 210 }
cisco6400Nrp    OBJECT IDENTIFIER ::= { ciscoProducts 211 }
cisco801        OBJECT IDENTIFIER ::= { ciscoProducts 212 }
cisco802        OBJECT IDENTIFIER ::= { ciscoProducts 213 }
cisco803        OBJECT IDENTIFIER ::= { ciscoProducts 214 }
cisco804        OBJECT IDENTIFIER ::= { ciscoProducts 215 }
cisco1750       OBJECT IDENTIFIER ::= { ciscoProducts 216 }
catalyst2924XLv OBJECT IDENTIFIER ::= { ciscoProducts 217 }
catalyst2924CXLv OBJECT IDENTIFIER ::= { ciscoProducts 218 }
catalyst2912XL  OBJECT IDENTIFIER ::= { ciscoProducts 219 }
catalyst2924MXL OBJECT IDENTIFIER ::= { ciscoProducts 220 }
catalyst2912MfXL OBJECT IDENTIFIER ::= { ciscoProducts 221 }
cisco7206VXR    OBJECT IDENTIFIER ::= { ciscoProducts 222 }
cisco7204VXR    OBJECT IDENTIFIER ::= { ciscoProducts 223 }
cisco1538M      OBJECT IDENTIFIER ::= { ciscoProducts 224 }
cisco1548M      OBJECT IDENTIFIER ::= { ciscoProducts 225 }
ciscoFasthub100 OBJECT IDENTIFIER ::= { ciscoProducts 226 }
ciscoPIXFirewall OBJECT IDENTIFIER ::= { ciscoProducts 227 }
ciscoMGX8850    OBJECT IDENTIFIER ::= { ciscoProducts 228 }
ciscoMGX8830    OBJECT IDENTIFIER ::= { ciscoProducts 229 }
catalyst8510msr OBJECT IDENTIFIER ::= { ciscoProducts 230 }
catalyst8515msr OBJECT IDENTIFIER ::= { ciscoProducts 231 }
ciscoIGX8410    OBJECT IDENTIFIER ::= { ciscoProducts 232 }
ciscoIGX8420    OBJECT IDENTIFIER ::= { ciscoProducts 233 }
ciscoIGX8430    OBJECT IDENTIFIER ::= { ciscoProducts 234 }
ciscoIGX8450    OBJECT IDENTIFIER ::= { ciscoProducts 235 }
ciscoBPX8620    OBJECT IDENTIFIER ::= { ciscoProducts 237 }
ciscoBPX8650    OBJECT IDENTIFIER ::= { ciscoProducts 238 }
ciscoBPX8680    OBJECT IDENTIFIER ::= { ciscoProducts 239 }
ciscoCacheEngine OBJECT IDENTIFIER ::= { ciscoProducts 240 }
ciscoCat6000    OBJECT IDENTIFIER ::= { ciscoProducts 241 }
ciscoBPXSes     OBJECT IDENTIFIER ::= { ciscoProducts 242 }
ciscoIGXSes     OBJECT IDENTIFIER ::= { ciscoProducts 243 }
ciscoLocalDirector OBJECT IDENTIFIER ::= { ciscoProducts 244 }
cisco805        OBJECT IDENTIFIER ::= { ciscoProducts 245 }
catalyst3508GXL OBJECT IDENTIFIER ::= { ciscoProducts 246 }
catalyst3512XL  OBJECT IDENTIFIER ::= { ciscoProducts 247 }
catalyst3524XL  OBJECT IDENTIFIER ::= { ciscoProducts 248 }
cisco1407       OBJECT IDENTIFIER ::= { ciscoProducts 249 }
cisco1417       OBJECT IDENTIFIER ::= { ciscoProducts 250 }
cisco6100       OBJECT IDENTIFIER ::= { ciscoProducts 251 }
cisco6130       OBJECT IDENTIFIER ::= { ciscoProducts 252 }
cisco6260       OBJECT IDENTIFIER ::= { ciscoProducts 253 }
ciscoOpticalRegenerator OBJECT IDENTIFIER ::= { ciscoProducts 254 }
ciscoUBR924     OBJECT IDENTIFIER ::= { ciscoProducts 255 }
ciscoWSX6302Msm OBJECT IDENTIFIER ::= { ciscoProducts 256 }
catalyst5kRsfc  OBJECT IDENTIFIER ::= { ciscoProducts 257 }
catalyst6kMsfc  OBJECT IDENTIFIER ::= { ciscoProducts 258 }
cisco7120Quadt1 OBJECT IDENTIFIER ::= { ciscoProducts 259 }
cisco7120T3     OBJECT IDENTIFIER ::= { ciscoProducts 260 }
cisco7120E3     OBJECT IDENTIFIER ::= { ciscoProducts 261 }
cisco7120At3    OBJECT IDENTIFIER ::= { ciscoProducts 262 }
cisco7120Ae3    OBJECT IDENTIFIER ::= { ciscoProducts 263 }
cisco7120Smi3   OBJECT IDENTIFIER ::= { ciscoProducts 264 }
cisco7140Dualt3 OBJECT IDENTIFIER ::= { ciscoProducts 265 }
cisco7140Duale3 OBJECT IDENTIFIER ::= { ciscoProducts 266 }
cisco7140Dualat3 OBJECT IDENTIFIER ::= { ciscoProducts 267 }
cisco7140Dualae3 OBJECT IDENTIFIER ::= { ciscoProducts 268 }
cisco7140Dualmm3 OBJECT IDENTIFIER ::= { ciscoProducts 269 }
cisco827QuadV   OBJECT IDENTIFIER ::= { ciscoProducts 270 }
ciscoUBR7246VXR OBJECT IDENTIFIER ::= { ciscoProducts 271 }
cisco10400      OBJECT IDENTIFIER ::= { ciscoProducts 272 }
cisco12016      OBJECT IDENTIFIER ::= { ciscoProducts 273 }
ciscoAs5400     OBJECT IDENTIFIER ::= { ciscoProducts 274 }
cat2948gL3      OBJECT IDENTIFIER ::= { ciscoProducts 275 }
cisco7140Octt1  OBJECT IDENTIFIER ::= { ciscoProducts 276 }
cisco7140Dualfe OBJECT IDENTIFIER ::= { ciscoProducts 277 }
cat3548XL       OBJECT IDENTIFIER ::= { ciscoProducts 278 }
ciscoVG200      OBJECT IDENTIFIER ::= { ciscoProducts 279 }
cat6006         OBJECT IDENTIFIER ::= { ciscoProducts 280 }
cat6009         OBJECT IDENTIFIER ::= { ciscoProducts 281 }
cat6506         OBJECT IDENTIFIER ::= { ciscoProducts 282 }
cat6509         OBJECT IDENTIFIER ::= { ciscoProducts 283 }
cisco827        OBJECT IDENTIFIER ::= { ciscoProducts 284 }
ciscoManagementEngine1100 OBJECT IDENTIFIER ::= { ciscoProducts 285 }
ciscoMc3810V3   OBJECT IDENTIFIER ::= { ciscoProducts 286 }
cat3524tXLEn    OBJECT IDENTIFIER ::= { ciscoProducts 287 }
cisco7507z      OBJECT IDENTIFIER ::= { ciscoProducts 288 }
cisco7513z      OBJECT IDENTIFIER ::= { ciscoProducts 289 }
cisco7507mx     OBJECT IDENTIFIER ::= { ciscoProducts 290 }
cisco7513mx     OBJECT IDENTIFIER ::= { ciscoProducts 291 }
ciscoUBR912C    OBJECT IDENTIFIER ::= { ciscoProducts 292 }
ciscoUBR912S    OBJECT IDENTIFIER ::= { ciscoProducts 293 }
ciscoUBR914     OBJECT IDENTIFIER ::= { ciscoProducts 294 }
cisco802J       OBJECT IDENTIFIER ::= { ciscoProducts 295 }
cisco804J       OBJECT IDENTIFIER ::= { ciscoProducts 296 }
cisco6160       OBJECT IDENTIFIER ::= { ciscoProducts 297 }
cat4908gL3      OBJECT IDENTIFIER ::= { ciscoProducts 298 }
cisco6015       OBJECT IDENTIFIER ::= { ciscoProducts 299 }
cat4232L3       OBJECT IDENTIFIER ::= { ciscoProducts 300 }
catalyst6kMsfc2 OBJECT IDENTIFIER ::= { ciscoProducts 301 }
cisco7750Mrp200 OBJECT IDENTIFIER ::= { ciscoProducts 302 }
cisco7750Ssp80  OBJECT IDENTIFIER ::= { ciscoProducts 303 }
ciscoMGX8230    OBJECT IDENTIFIER ::= { ciscoProducts 304 }
ciscoMGX8250    OBJECT IDENTIFIER ::= { ciscoProducts 305 }
ciscoCVA122     OBJECT IDENTIFIER ::= { ciscoProducts 306 }
ciscoCVA124     OBJECT IDENTIFIER ::= { ciscoProducts 307 }
ciscoAs5850     OBJECT IDENTIFIER ::= { ciscoProducts 308 }
cat6509Sp       OBJECT IDENTIFIER ::= { ciscoProducts 310 }
ciscoMGX8240    OBJECT IDENTIFIER ::= { ciscoProducts 311 }
cat4840gL3      OBJECT IDENTIFIER ::= { ciscoProducts 312 }
ciscoAS5350     OBJECT IDENTIFIER ::= { ciscoProducts 313 }
cisco7750       OBJECT IDENTIFIER ::= { ciscoProducts 314 }
ciscoMGX8950    OBJECT IDENTIFIER ::= { ciscoProducts 315 }
ciscoUBR925     OBJECT IDENTIFIER ::= { ciscoProducts 316 }
ciscoUBR10012   OBJECT IDENTIFIER ::= { ciscoProducts 317 }
catalyst4kGateway OBJECT IDENTIFIER ::= { ciscoProducts 318 }
cisco2650       OBJECT IDENTIFIER ::= { ciscoProducts 319 }
cisco2651       OBJECT IDENTIFIER ::= { ciscoProducts 320 }
cisco826QuadV   OBJECT IDENTIFIER ::= { ciscoProducts 321 }
cisco826        OBJECT IDENTIFIER ::= { ciscoProducts 322 }
catalyst295012  OBJECT IDENTIFIER ::= { ciscoProducts 323 }
catalyst295024  OBJECT IDENTIFIER ::= { ciscoProducts 324 }
catalyst295024C OBJECT IDENTIFIER ::= { ciscoProducts 325 }
cisco1751       OBJECT IDENTIFIER ::= { ciscoProducts 326 }
cisco626        OBJECT IDENTIFIER ::= { ciscoProducts 329 }
cisco627        OBJECT IDENTIFIER ::= { ciscoProducts 330 }
cisco633        OBJECT IDENTIFIER ::= { ciscoProducts 331 }
cisco673        OBJECT IDENTIFIER ::= { ciscoProducts 332 }
cisco675        OBJECT IDENTIFIER ::= { ciscoProducts 333 }
cisco675e       OBJECT IDENTIFIER ::= { ciscoProducts 334 }
cisco676        OBJECT IDENTIFIER ::= { ciscoProducts 335 }
cisco677        OBJECT IDENTIFIER ::= { ciscoProducts 336 }
cisco678        OBJECT IDENTIFIER ::= { ciscoProducts 337 }
cisco3661Ac     OBJECT IDENTIFIER ::= { ciscoProducts 338 }
cisco3661Dc     OBJECT IDENTIFIER ::= { ciscoProducts 339 }
cisco3662Ac     OBJECT IDENTIFIER ::= { ciscoProducts 340 }
cisco3662Dc     OBJECT IDENTIFIER ::= { ciscoProducts 341 }
cisco3662AcCo   OBJECT IDENTIFIER ::= { ciscoProducts 342 }
cisco3662DcCo   OBJECT IDENTIFIER ::= { ciscoProducts 343 }
ciscoUBR7111    OBJECT IDENTIFIER ::= { ciscoProducts 344 }
ciscoUBR7111E   OBJECT IDENTIFIER ::= { ciscoProducts 345 }
ciscoUBR7114    OBJECT IDENTIFIER ::= { ciscoProducts 346 }
ciscoUBR7114E   OBJECT IDENTIFIER ::= { ciscoProducts 347 }
cisco12010      OBJECT IDENTIFIER ::= { ciscoProducts 348 }
cisco8110       OBJECT IDENTIFIER ::= { ciscoProducts 349 }
ciscoUBR905     OBJECT IDENTIFIER ::= { ciscoProducts 351 }
ciscoSOHO77     OBJECT IDENTIFIER ::= { ciscoProducts 353 }
ciscoSOHO76     OBJECT IDENTIFIER ::= { ciscoProducts 354 }
cisco7150Dualfe OBJECT IDENTIFIER ::= { ciscoProducts 355 }
cisco7150Octt1  OBJECT IDENTIFIER ::= { ciscoProducts 356 }
cisco7150Dualt3 OBJECT IDENTIFIER ::= { ciscoProducts 357 }
ciscoOlympus    OBJECT IDENTIFIER ::= { ciscoProducts 358 }
catalyst2950t24 OBJECT IDENTIFIER ::= { ciscoProducts 359 }
ciscoVPS1110    OBJECT IDENTIFIER ::= { ciscoProducts 360 }
ciscoContentEngine OBJECT IDENTIFIER ::= { ciscoProducts 361 }
ciscoIAD2420    OBJECT IDENTIFIER ::= { ciscoProducts 362 }
cisco677i       OBJECT IDENTIFIER ::= { ciscoProducts 363 }
cisco674        OBJECT IDENTIFIER ::= { ciscoProducts 364 }
ciscoDPA7630    OBJECT IDENTIFIER ::= { ciscoProducts 365 }
catalyst355024  OBJECT IDENTIFIER ::= { ciscoProducts 366 }
catalyst355048  OBJECT IDENTIFIER ::= { ciscoProducts 367 }
catalyst355012T OBJECT IDENTIFIER ::= { ciscoProducts 368 }
catalyst2924LREXL OBJECT IDENTIFIER ::= { ciscoProducts 369 }
catalyst2912LREXL OBJECT IDENTIFIER ::= { ciscoProducts 370 }
ciscoCVA122E    OBJECT IDENTIFIER ::= { ciscoProducts 371 }
ciscoCVA124E    OBJECT IDENTIFIER ::= { ciscoProducts 372 }
ciscoURM        OBJECT IDENTIFIER ::= { ciscoProducts 373 }
ciscoURM2FE     OBJECT IDENTIFIER ::= { ciscoProducts 374 }
ciscoURM2FE2V   OBJECT IDENTIFIER ::= { ciscoProducts 375 }
cisco7401VXR    OBJECT IDENTIFIER ::= { ciscoProducts 376 }
ciscoCAP340     OBJECT IDENTIFIER ::= { ciscoProducts 379 }
ciscoCAP350     OBJECT IDENTIFIER ::= { ciscoProducts 380 }
ciscoDPA7610    OBJECT IDENTIFIER ::= { ciscoProducts 381 }
cisco828        OBJECT IDENTIFIER ::= { ciscoProducts 382 }
cisco806        OBJECT IDENTIFIER ::= { ciscoProducts 384 }
cisco12416      OBJECT IDENTIFIER ::= { ciscoProducts 385 }
cat2948gL3Dc    OBJECT IDENTIFIER ::= { ciscoProducts 386 }
cat4908gL3Dc    OBJECT IDENTIFIER ::= { ciscoProducts 387 }
cisco12406      OBJECT IDENTIFIER ::= { ciscoProducts 388 }
ciscoPIXFirewall506 OBJECT IDENTIFIER ::= { ciscoProducts 389 }
ciscoPIXFirewall515 OBJECT IDENTIFIER ::= { ciscoProducts 390 }
ciscoPIXFirewall520 OBJECT IDENTIFIER ::= { ciscoProducts 391 }
ciscoPIXFirewall525 OBJECT IDENTIFIER ::= { ciscoProducts 392 }
ciscoPIXFirewall535 OBJECT IDENTIFIER ::= { ciscoProducts 393 }
cisco12410      OBJECT IDENTIFIER ::= { ciscoProducts 394 }
cisco811        OBJECT IDENTIFIER ::= { ciscoProducts 395 }
cisco813        OBJECT IDENTIFIER ::= { ciscoProducts 396 }
cisco10720      OBJECT IDENTIFIER ::= { ciscoProducts 397 }
ciscoMWR1900    OBJECT IDENTIFIER ::= { ciscoProducts 398 }
cisco4224       OBJECT IDENTIFIER ::= { ciscoProducts 399 }
ciscoWSC6513    OBJECT IDENTIFIER ::= { ciscoProducts 400 }
cisco7603       OBJECT IDENTIFIER ::= { ciscoProducts 401 }
cisco7606       OBJECT IDENTIFIER ::= { ciscoProducts 402 }
cisco7401ASR    OBJECT IDENTIFIER ::= { ciscoProducts 403 }
ciscoVG248      OBJECT IDENTIFIER ::= { ciscoProducts 404 }
ciscoHSE        OBJECT IDENTIFIER ::= { ciscoProducts 405 }
ciscoONS15540ESP OBJECT IDENTIFIER ::= { ciscoProducts 406 }
ciscoSN5420     OBJECT IDENTIFIER ::= { ciscoProducts 407 }
ciscoCe507      OBJECT IDENTIFIER ::= { ciscoProducts 409 }
ciscoCe560      OBJECT IDENTIFIER ::= { ciscoProducts 410 }
ciscoCe590      OBJECT IDENTIFIER ::= { ciscoProducts 411 }
ciscoCe7320     OBJECT IDENTIFIER ::= { ciscoProducts 412 }
cisco2691       OBJECT IDENTIFIER ::= { ciscoProducts 413 }
cisco3725       OBJECT IDENTIFIER ::= { ciscoProducts 414 }
cisco1760       OBJECT IDENTIFIER ::= { ciscoProducts 416 }
ciscoPIXFirewall501 OBJECT IDENTIFIER ::= { ciscoProducts 417 }
cisco2610M      OBJECT IDENTIFIER ::= { ciscoProducts 418 }
cisco2611M      OBJECT IDENTIFIER ::= { ciscoProducts 419 }
cisco12404      OBJECT IDENTIFIER ::= { ciscoProducts 423 }
cisco9004       OBJECT IDENTIFIER ::= { ciscoProducts 424 }
cisco3631Co     OBJECT IDENTIFIER ::= { ciscoProducts 425 }
catalyst295012G OBJECT IDENTIFIER ::= { ciscoProducts 427 }
catalyst295024G OBJECT IDENTIFIER ::= { ciscoProducts 428 }
catalyst295048G OBJECT IDENTIFIER ::= { ciscoProducts 429 }
catalyst295024S OBJECT IDENTIFIER ::= { ciscoProducts 430 }
catalyst355012G OBJECT IDENTIFIER ::= { ciscoProducts 431 }
ciscoCE507AV    OBJECT IDENTIFIER ::= { ciscoProducts 432 }
ciscoCE560AV    OBJECT IDENTIFIER ::= { ciscoProducts 433 }
ciscoIE2105     OBJECT IDENTIFIER ::= { ciscoProducts 434 }
ciscoMGX8850Pxm1E OBJECT IDENTIFIER ::= { ciscoProducts 435 }
cisco3745       OBJECT IDENTIFIER ::= { ciscoProducts 436 }
cisco10005      OBJECT IDENTIFIER ::= { ciscoProducts 437 }
cisco10008      OBJECT IDENTIFIER ::= { ciscoProducts 438 }
cisco7304       OBJECT IDENTIFIER ::= { ciscoProducts 439 }
ciscoRpmXf      OBJECT IDENTIFIER ::= { ciscoProducts 440 }
cisco1721       OBJECT IDENTIFIER ::= { ciscoProducts 444 }
cisco827H       OBJECT IDENTIFIER ::= { ciscoProducts 446 }
cat4006         OBJECT IDENTIFIER ::= { ciscoProducts 448 }
ciscoWSC6503    OBJECT IDENTIFIER ::= { ciscoProducts 449 }
ciscoPIXFirewall506E OBJECT IDENTIFIER ::= { ciscoProducts 450 }
ciscoPIXFirewall515E OBJECT IDENTIFIER ::= { ciscoProducts 451 }
cat355024Dc     OBJECT IDENTIFIER ::= { ciscoProducts 452 }
cat355024Mmf    OBJECT IDENTIFIER ::= { ciscoProducts 453 }
ciscoCE2636     OBJECT IDENTIFIER ::= { ciscoProducts 454 }
ciscoDwCE       OBJECT IDENTIFIER ::= { ciscoProducts 455 }
cisco7750Mrp300 OBJECT IDENTIFIER ::= { ciscoProducts 456 }
ciscoRPMPR      OBJECT IDENTIFIER ::= { ciscoProducts 457 }
cisco14MGX8830Pxm1E OBJECT IDENTIFIER ::= { ciscoProducts 458 }
ciscoWlse       OBJECT IDENTIFIER ::= { ciscoProducts 459 }
ciscoONS15530   OBJECT IDENTIFIER ::= { ciscoProducts 460 }
ciscoONS15530NEBS OBJECT IDENTIFIER ::= { ciscoProducts 461 }
ciscoONS15530ETSI OBJECT IDENTIFIER ::= { ciscoProducts 462 }
cisco6400UAC    OBJECT IDENTIFIER ::= { ciscoProducts 464 }
ciscoAIRAP1200  OBJECT IDENTIFIER ::= { ciscoProducts 474 }
ciscoSN5428     OBJECT IDENTIFIER ::= { ciscoProducts 475 }
cisco2610XM     OBJECT IDENTIFIER ::= { ciscoProducts 466 }
cisco2611XM     OBJECT IDENTIFIER ::= { ciscoProducts 467 }
cisco2620XM     OBJECT IDENTIFIER ::= { ciscoProducts 468 }
cisco2621XM     OBJECT IDENTIFIER ::= { ciscoProducts 469 }
cisco2650XM     OBJECT IDENTIFIER ::= { ciscoProducts 470 }
cisco2651XM     OBJECT IDENTIFIER ::= { ciscoProducts 471 }
catalyst295024GDC OBJECT IDENTIFIER ::= { ciscoProducts 472 }
cisco7301       OBJECT IDENTIFIER ::= { ciscoProducts 476 }
cisco12816      OBJECT IDENTIFIER ::= { ciscoProducts 477 }
cisco12810      OBJECT IDENTIFIER ::= { ciscoProducts 478 }
cisco3250       OBJECT IDENTIFIER ::= { ciscoProducts 479 }
catalyst295024SX OBJECT IDENTIFIER ::= { ciscoProducts 480 }
ciscoONS15540ESPx OBJECT IDENTIFIER ::= { ciscoProducts 481 }
catalyst295024LRESt OBJECT IDENTIFIER ::= { ciscoProducts 482 }
catalyst29508LRESt OBJECT IDENTIFIER ::= { ciscoProducts 483 }
catalyst295024LREG OBJECT IDENTIFIER ::= { ciscoProducts 484 }
catalyst355024PWR OBJECT IDENTIFIER ::= { ciscoProducts 485 }
ciscoCDM4630    OBJECT IDENTIFIER ::= { ciscoProducts 486 }
ciscoCDM4650    OBJECT IDENTIFIER ::= { ciscoProducts 487 }
catalyst2955T12 OBJECT IDENTIFIER ::= { ciscoProducts 488 }
catalyst2955C12 OBJECT IDENTIFIER ::= { ciscoProducts 489 }
ciscoCE508      OBJECT IDENTIFIER ::= { ciscoProducts 490 }
ciscoCE565      OBJECT IDENTIFIER ::= { ciscoProducts 491 }
ciscoCE7325     OBJECT IDENTIFIER ::= { ciscoProducts 492 }
ciscoONS15454   OBJECT IDENTIFIER ::= { ciscoProducts 493 }
ciscoONS15327   OBJECT IDENTIFIER ::= { ciscoProducts 494 }
cisco837        OBJECT IDENTIFIER ::= { ciscoProducts 495 }
ciscoSOHO97     OBJECT IDENTIFIER ::= { ciscoProducts 496 }
cisco831        OBJECT IDENTIFIER ::= { ciscoProducts 497 }
ciscoSOHO91     OBJECT IDENTIFIER ::= { ciscoProducts 498 }
cisco836        OBJECT IDENTIFIER ::= { ciscoProducts 499 }
ciscoSOHO96     OBJECT IDENTIFIER ::= { ciscoProducts 500 }
cat4507         OBJECT IDENTIFIER ::= { ciscoProducts 501 }
cat4506         OBJECT IDENTIFIER ::= { ciscoProducts 502 }
cat4503         OBJECT IDENTIFIER ::= { ciscoProducts 503 }
ciscoCE7305     OBJECT IDENTIFIER ::= { ciscoProducts 504 }
ciscoCE510      OBJECT IDENTIFIER ::= { ciscoProducts 505 }
ciscoAIRAP1100  OBJECT IDENTIFIER ::= { ciscoProducts 507 }
catalyst2955S12 OBJECT IDENTIFIER ::= { ciscoProducts 508 }
cisco7609       OBJECT IDENTIFIER ::= { ciscoProducts 509 }
catalyst375024  OBJECT IDENTIFIER ::= { ciscoProducts 511 }
catalyst375048  OBJECT IDENTIFIER ::= { ciscoProducts 512 }
catalyst375024TS OBJECT IDENTIFIER ::= { ciscoProducts 513 }
catalyst375024T OBJECT IDENTIFIER ::= { ciscoProducts 514 }
catalyst37xxStack OBJECT IDENTIFIER ::= { ciscoProducts 516 }
ciscoGSS        OBJECT IDENTIFIER ::= { ciscoProducts 517 }
ciscoPrimaryGSSM OBJECT IDENTIFIER ::= { ciscoProducts 518 }
ciscoStandbyGSSM OBJECT IDENTIFIER ::= { ciscoProducts 519 }
ciscoMWR1941DC  OBJECT IDENTIFIER ::= { ciscoProducts 520 }
ciscoDSC9216K9  OBJECT IDENTIFIER ::= { ciscoProducts 521 }
cat6500FirewallSm OBJECT IDENTIFIER ::= { ciscoProducts 522 }
ciscoCSM        OBJECT IDENTIFIER ::= { ciscoProducts 524 }
ciscoAIRAP1210  OBJECT IDENTIFIER ::= { ciscoProducts 525 }
catalyst297024  OBJECT IDENTIFIER ::= { ciscoProducts 527 }
cisco7613       OBJECT IDENTIFIER ::= { ciscoProducts 528 }
catalyst3750Ge12Sfp OBJECT IDENTIFIER ::= { ciscoProducts 530 }
ciscoCR4430     OBJECT IDENTIFIER ::= { ciscoProducts 531 }
ciscoCR4450     OBJECT IDENTIFIER ::= { ciscoProducts 532 }
ciscoAIRBR1410  OBJECT IDENTIFIER ::= { ciscoProducts 533 }
ciscoWSC6509neba OBJECT IDENTIFIER ::= { ciscoProducts 534 }
catalyst375048PS OBJECT IDENTIFIER ::= { ciscoProducts 535 }
catalyst375024PS OBJECT IDENTIFIER ::= { ciscoProducts 536 }
catalyst4510    OBJECT IDENTIFIER ::= { ciscoProducts 537 }
cisco1711       OBJECT IDENTIFIER ::= { ciscoProducts 538 }
cisco1712       OBJECT IDENTIFIER ::= { ciscoProducts 539 }
catalyst29408TT OBJECT IDENTIFIER ::= { ciscoProducts 540 }
catalyst29408TF OBJECT IDENTIFIER ::= { ciscoProducts 542 }
cisco3825       OBJECT IDENTIFIER ::= { ciscoProducts 543 }
cisco3845       OBJECT IDENTIFIER ::= { ciscoProducts 544 }
cisco2430Iad24Fxs OBJECT IDENTIFIER ::= { ciscoProducts 545 }
cisco2431Iad8Fxs OBJECT IDENTIFIER ::= { ciscoProducts 546 }
cisco2431Iad16Fxs OBJECT IDENTIFIER ::= { ciscoProducts 547 }
cisco2431Iad1T1E1 OBJECT IDENTIFIER ::= { ciscoProducts 548 }
cisco2432Iad24Fxs OBJECT IDENTIFIER ::= { ciscoProducts 549 }
cisco1701ADSLBRI OBJECT IDENTIFIER ::= { ciscoProducts 550 }
catalyst2950St24LRE997 OBJECT IDENTIFIER ::= { ciscoProducts 551 }
ciscoAirAp350IOS OBJECT IDENTIFIER ::= { ciscoProducts 552 }
cisco3220       OBJECT IDENTIFIER ::= { ciscoProducts 553 }
cat6500SslSm    OBJECT IDENTIFIER ::= { ciscoProducts 554 }
ciscoSIMSE      OBJECT IDENTIFIER ::= { ciscoProducts 555 }
ciscoESSE       OBJECT IDENTIFIER ::= { ciscoProducts 556 }
catalyst6kSup720 OBJECT IDENTIFIER ::= { ciscoProducts 557 }
ciscoVG224      OBJECT IDENTIFIER ::= { ciscoProducts 558 }
catalyst295048T OBJECT IDENTIFIER ::= { ciscoProducts 559 }
catalyst295048SX OBJECT IDENTIFIER ::= { ciscoProducts 560 }
catalyst297024TS OBJECT IDENTIFIER ::= { ciscoProducts 561 }
ciscoNmNam      OBJECT IDENTIFIER ::= { ciscoProducts 562 }
catalyst356024PS OBJECT IDENTIFIER ::= { ciscoProducts 563 }
catalyst356048PS OBJECT IDENTIFIER ::= { ciscoProducts 564 }
ciscoAIRBR1300  OBJECT IDENTIFIER ::= { ciscoProducts 565 }
cisco851        OBJECT IDENTIFIER ::= { ciscoProducts 566 }
cisco857        OBJECT IDENTIFIER ::= { ciscoProducts 567 }
cisco876        OBJECT IDENTIFIER ::= { ciscoProducts 568 }
cisco877        OBJECT IDENTIFIER ::= { ciscoProducts 569 }
cisco878        OBJECT IDENTIFIER ::= { ciscoProducts 570 }
cisco871        OBJECT IDENTIFIER ::= { ciscoProducts 571 }
catalyst6kGateway OBJECT IDENTIFIER ::= { ciscoProducts 573 }
catalyst375024ME OBJECT IDENTIFIER ::= { ciscoProducts 574 }
catalyst4000NAM OBJECT IDENTIFIER ::= { ciscoProducts 575 }
cisco2811       OBJECT IDENTIFIER ::= { ciscoProducts 576 }
cisco2821       OBJECT IDENTIFIER ::= { ciscoProducts 577 }
cisco2851       OBJECT IDENTIFIER ::= { ciscoProducts 578 }
ciscoMCS7815I   OBJECT IDENTIFIER ::= { ciscoProducts 582 }
ciscoMCS7825H   OBJECT IDENTIFIER ::= { ciscoProducts 583 }
ciscoMCS7835H   OBJECT IDENTIFIER ::= { ciscoProducts 584 }
ciscoMCS7835I   OBJECT IDENTIFIER ::= { ciscoProducts 585 }
ciscoMCS7845H   OBJECT IDENTIFIER ::= { ciscoProducts 586 }
ciscoMCS7845I   OBJECT IDENTIFIER ::= { ciscoProducts 587 }
ciscoMCS7855I   OBJECT IDENTIFIER ::= { ciscoProducts 588 }
ciscoMCS7865I   OBJECT IDENTIFIER ::= { ciscoProducts 589 }
cisco12006      OBJECT IDENTIFIER ::= { ciscoProducts 590 }
catalyst3750G16TD OBJECT IDENTIFIER ::= { ciscoProducts 591 }
ciscoIGESM      OBJECT IDENTIFIER ::= { ciscoProducts 592 }
ciscoCCM        OBJECT IDENTIFIER ::= { ciscoProducts 593 }
ciscoCe511K9    OBJECT IDENTIFIER ::= { ciscoProducts 595 }
ciscoCe566K9    OBJECT IDENTIFIER ::= { ciscoProducts 596 }
ciscoMGX8880    OBJECT IDENTIFIER ::= { ciscoProducts 598 }
ciscoWsSvcWLAN1K9 OBJECT IDENTIFIER ::= { ciscoProducts 599 }
ciscoCe7306K9   OBJECT IDENTIFIER ::= { ciscoProducts 600 }
ciscoCe7326K9   OBJECT IDENTIFIER ::= { ciscoProducts 601 }
catalyst3750G24PS OBJECT IDENTIFIER ::= { ciscoProducts 602 }
catalyst3750G48PS OBJECT IDENTIFIER ::= { ciscoProducts 603 }
catalyst3750G48TS OBJECT IDENTIFIER ::= { ciscoProducts 604 }
ciscoBMGX8830Pxm45 OBJECT IDENTIFIER ::= { ciscoProducts 606 }
ciscoBMGX8830Pxm1E OBJECT IDENTIFIER ::= { ciscoProducts 607 }
ciscoBMGX8850Pxm45 OBJECT IDENTIFIER ::= { ciscoProducts 608 }
ciscoBMGX8850Pxm1E OBJECT IDENTIFIER ::= { ciscoProducts 609 }
ciscoNetworkRegistrar OBJECT IDENTIFIER ::= { ciscoProducts 611 }
ciscoCe501K9    OBJECT IDENTIFIER ::= { ciscoProducts 612 }
ciscoCRS16S     OBJECT IDENTIFIER ::= { ciscoProducts 613 }
catalyst3560G24PS OBJECT IDENTIFIER ::= { ciscoProducts 614 }
catalyst3560G24TS OBJECT IDENTIFIER ::= { ciscoProducts 615 }
catalyst3560G48PS OBJECT IDENTIFIER ::= { ciscoProducts 616 }
catalyst3560G48TS OBJECT IDENTIFIER ::= { ciscoProducts 617 }
ciscoAIRAP1130  OBJECT IDENTIFIER ::= { ciscoProducts 618 }
cisco2801       OBJECT IDENTIFIER ::= { ciscoProducts 619 }
cisco1841       OBJECT IDENTIFIER ::= { ciscoProducts 620 }
ciscoWsSvcMWAM1 OBJECT IDENTIFIER ::= { ciscoProducts 621 }
ciscoNMCUE      OBJECT IDENTIFIER ::= { ciscoProducts 622 }
ciscoAIMCUE     OBJECT IDENTIFIER ::= { ciscoProducts 623 }
catalyst3750G24TS1U OBJECT IDENTIFIER ::= { ciscoProducts 624 }
cisco371098HP001 OBJECT IDENTIFIER ::= { ciscoProducts 625 }
catalyst4948    OBJECT IDENTIFIER ::= { ciscoProducts 626 }
ciscoWLSE1130   OBJECT IDENTIFIER ::= { ciscoProducts 630 }
ciscoWLSE1030   OBJECT IDENTIFIER ::= { ciscoProducts 631 }
ciscoHSE1140    OBJECT IDENTIFIER ::= { ciscoProducts 632 }
catalyst356024TS OBJECT IDENTIFIER ::= { ciscoProducts 633 }
catalyst356048TS OBJECT IDENTIFIER ::= { ciscoProducts 634 }
cisco1801       OBJECT IDENTIFIER ::= { ciscoProducts 638 }
cisco1802       OBJECT IDENTIFIER ::= { ciscoProducts 639 }
cisco1803       OBJECT IDENTIFIER ::= { ciscoProducts 640 }
cisco1811       OBJECT IDENTIFIER ::= { ciscoProducts 641 }
cisco1812       OBJECT IDENTIFIER ::= { ciscoProducts 642 }
ciscoCRS8S      OBJECT IDENTIFIER ::= { ciscoProducts 643 }
ciscoIDS4210    OBJECT IDENTIFIER ::= { ciscoProducts 645 }
ciscoIDS4215    OBJECT IDENTIFIER ::= { ciscoProducts 646 }
ciscoIDS4235    OBJECT IDENTIFIER ::= { ciscoProducts 647 }
ciscoIPS4240    OBJECT IDENTIFIER ::= { ciscoProducts 648 }
ciscoIDS4250    OBJECT IDENTIFIER ::= { ciscoProducts 649 }
ciscoIDS4250SX  OBJECT IDENTIFIER ::= { ciscoProducts 650 }
ciscoIDS4250XL  OBJECT IDENTIFIER ::= { ciscoProducts 651 }
ciscoIPS4255    OBJECT IDENTIFIER ::= { ciscoProducts 652 }
ciscoIDSIDSM2   OBJECT IDENTIFIER ::= { ciscoProducts 653 }
ciscoIDSNMCIDS  OBJECT IDENTIFIER ::= { ciscoProducts 654 }
ciscoIPSSSM20   OBJECT IDENTIFIER ::= { ciscoProducts 655 }
catalyst375024FS OBJECT IDENTIFIER ::= { ciscoProducts 656 }
ciscoWSC6504E   OBJECT IDENTIFIER ::= { ciscoProducts 657 }
cisco7604       OBJECT IDENTIFIER ::= { ciscoProducts 658 }
catalyst494810GE OBJECT IDENTIFIER ::= { ciscoProducts 659 }
ciscoIGESMSFP   OBJECT IDENTIFIER ::= { ciscoProducts 660 }
ciscoFE6326K9   OBJECT IDENTIFIER ::= { ciscoProducts 661 }
ciscoIPSSSM10   OBJECT IDENTIFIER ::= { ciscoProducts 662 }
ciscoNme16Es1Ge OBJECT IDENTIFIER ::= { ciscoProducts 663 }
ciscoNmeX24Es1Ge OBJECT IDENTIFIER ::= { ciscoProducts 664 }
ciscoNmeXd24Es2St OBJECT IDENTIFIER ::= { ciscoProducts 665 }
ciscoNmeXd48Es2Ge OBJECT IDENTIFIER ::= { ciscoProducts 666 }
ciscoAs5400XM   OBJECT IDENTIFIER ::= { ciscoProducts 668 }
ciscoASA5510    OBJECT IDENTIFIER ::= { ciscoProducts 669 }
ciscoASA5520    OBJECT IDENTIFIER ::= { ciscoProducts 670 }
ciscoASA5520sc  OBJECT IDENTIFIER ::= { ciscoProducts 671 }
ciscoASA5540    OBJECT IDENTIFIER ::= { ciscoProducts 672 }
ciscoASA5540sc  OBJECT IDENTIFIER ::= { ciscoProducts 673 }
ciscoWsSvcFwm1sc OBJECT IDENTIFIER ::= { ciscoProducts 674 }
ciscoPIXFirewall535sc OBJECT IDENTIFIER ::= { ciscoProducts 675 }
ciscoPIXFirewall525sc OBJECT IDENTIFIER ::= { ciscoProducts 676 }
ciscoPIXFirewall515Esc OBJECT IDENTIFIER ::= { ciscoProducts 677 }
ciscoPIXFirewall515sc OBJECT IDENTIFIER ::= { ciscoProducts 678 }
ciscoAs5350XM   OBJECT IDENTIFIER ::= { ciscoProducts 679 }
ciscoFe7326K9   OBJECT IDENTIFIER ::= { ciscoProducts 680 }
ciscoFe511K9    OBJECT IDENTIFIER ::= { ciscoProducts 681 }
ciscoSCEDispatcher OBJECT IDENTIFIER ::= { ciscoProducts 682 }
ciscoSCE1000    OBJECT IDENTIFIER ::= { ciscoProducts 683 }
ciscoSCE2000    OBJECT IDENTIFIER ::= { ciscoProducts 684 }
ciscoAIRAP1240  OBJECT IDENTIFIER ::= { ciscoProducts 685 }
ciscoDSC9120CLK9 OBJECT IDENTIFIER ::= { ciscoProducts 686 }
ciscoFe611K9    OBJECT IDENTIFIER ::= { ciscoProducts 687 }
catalyst3750Ge12SfpDc OBJECT IDENTIFIER ::= { ciscoProducts 688 }
ciscoICM        OBJECT IDENTIFIER ::= { ciscoProducts 693 }
catalyst296024  OBJECT IDENTIFIER ::= { ciscoProducts 694 }
catalyst296048  OBJECT IDENTIFIER ::= { ciscoProducts 695 }
catalyst2960G24 OBJECT IDENTIFIER ::= { ciscoProducts 696 }
catalyst2960G48 OBJECT IDENTIFIER ::= { ciscoProducts 697 }
ciscoNme16Es1GeNoPwr OBJECT IDENTIFIER ::= { ciscoProducts 702 }
ciscoNmeX24Es1GeNoPwr OBJECT IDENTIFIER ::= { ciscoProducts 703 }
ciscoNmeXd24Es2StNoPwr OBJECT IDENTIFIER ::= { ciscoProducts 704 }
ciscoNmeXd48Es2GeNoPwr OBJECT IDENTIFIER ::= { ciscoProducts 705 }
catalyst6kMsfc2a OBJECT IDENTIFIER ::= { ciscoProducts 706 }
ciscoEDI        OBJECT IDENTIFIER ::= { ciscoProducts 707 }
ciscoCe611K9    OBJECT IDENTIFIER ::= { ciscoProducts 708 }
ciscoWLSEs20    OBJECT IDENTIFIER ::= { ciscoProducts 709 }
ciscoMPX        OBJECT IDENTIFIER ::= { ciscoProducts 710 }
ciscoNMCUEEC    OBJECT IDENTIFIER ::= { ciscoProducts 711 }
ciscoWLSE1132   OBJECT IDENTIFIER ::= { ciscoProducts 712 }
ciscoME6340ACA  OBJECT IDENTIFIER ::= { ciscoProducts 713 }
ciscoME6340DCA  OBJECT IDENTIFIER ::= { ciscoProducts 714 }
ciscoME6340DCB  OBJECT IDENTIFIER ::= { ciscoProducts 715 }
catalyst296024TT OBJECT IDENTIFIER ::= { ciscoProducts 716 }
catalyst296048TT OBJECT IDENTIFIER ::= { ciscoProducts 717 }
ciscoIGESMSFPT  OBJECT IDENTIFIER ::= { ciscoProducts 718 }
ciscoMEC6524gs8s OBJECT IDENTIFIER ::= { ciscoProducts 719 }
ciscoMEC6524gt8s OBJECT IDENTIFIER ::= { ciscoProducts 720 }
ciscoPaldron    OBJECT IDENTIFIER ::= { ciscoProducts 723 }
catalystsExpress50024TT OBJECT IDENTIFIER ::= { ciscoProducts 724 }
catalystsExpress50024LC OBJECT IDENTIFIER ::= { ciscoProducts 725 }
catalystsExpress50024PC OBJECT IDENTIFIER ::= { ciscoProducts 726 }
catalystsExpress50012TC OBJECT IDENTIFIER ::= { ciscoProducts 727 }
ciscoIGESMT     OBJECT IDENTIFIER ::= { ciscoProducts 728 }
ciscoACE10K9    OBJECT IDENTIFIER ::= { ciscoProducts 730 }
cisco5750       OBJECT IDENTIFIER ::= { ciscoProducts 731 }
ciscoMWR1941DCA OBJECT IDENTIFIER ::= { ciscoProducts 732 }
cisco815        OBJECT IDENTIFIER ::= { ciscoProducts 733 }
cisco240024TSA  OBJECT IDENTIFIER ::= { ciscoProducts 734 }
cisco240024TSD  OBJECT IDENTIFIER ::= { ciscoProducts 735 }
cisco340024TSA  OBJECT IDENTIFIER ::= { ciscoProducts 736 }
cisco340024TSD  OBJECT IDENTIFIER ::= { ciscoProducts 737 }
ciscoCrs18Linecard OBJECT IDENTIFIER ::= { ciscoProducts 738 }
ciscoCrs1Fabric OBJECT IDENTIFIER ::= { ciscoProducts 739 }
ciscoFE2636     OBJECT IDENTIFIER ::= { ciscoProducts 740 }
ciscoIDS4220    OBJECT IDENTIFIER ::= { ciscoProducts 741 }
ciscoIDS4230    OBJECT IDENTIFIER ::= { ciscoProducts 742 }
ciscoIPS4260    OBJECT IDENTIFIER ::= { ciscoProducts 743 }
ciscoWsSvcSAMIBB OBJECT IDENTIFIER ::= { ciscoProducts 744 }
ciscoASA5505    OBJECT IDENTIFIER ::= { ciscoProducts 745 }
ciscoMCS7825I   OBJECT IDENTIFIER ::= { ciscoProducts 746 }
ciscoWsC3750g24ps OBJECT IDENTIFIER ::= { ciscoProducts 747 }
ciscoWs3020Hpq  OBJECT IDENTIFIER ::= { ciscoProducts 748 }
ciscoWs3030Del  OBJECT IDENTIFIER ::= { ciscoProducts 749 }
ciscoSpaOc48posSfp OBJECT IDENTIFIER ::= { ciscoProducts 750 }
ciscoWLSE1133   OBJECT IDENTIFIER ::= { ciscoProducts 752 }
ciscoASA5550    OBJECT IDENTIFIER ::= { ciscoProducts 753 }
ciscoNMAONK9    OBJECT IDENTIFIER ::= { ciscoProducts 754 }
ciscoNMAONWS    OBJECT IDENTIFIER ::= { ciscoProducts 755 }
ciscoNMAONAPS   OBJECT IDENTIFIER ::= { ciscoProducts 756 }
ciscoWae612K9   OBJECT IDENTIFIER ::= { ciscoProducts 757 }
ciscoAIRAP1250  OBJECT IDENTIFIER ::= { ciscoProducts 758 }
ciscoCe512K9    OBJECT IDENTIFIER ::= { ciscoProducts 759 }
ciscoFe512K9    OBJECT IDENTIFIER ::= { ciscoProducts 760 }
ciscoCe612K9    OBJECT IDENTIFIER ::= { ciscoProducts 761 }
ciscoFe612K9    OBJECT IDENTIFIER ::= { ciscoProducts 762 }
ciscoASA5550sc  OBJECT IDENTIFIER ::= { ciscoProducts 763 }
ciscoASA5520sy  OBJECT IDENTIFIER ::= { ciscoProducts 764 }
ciscoASA5540sy  OBJECT IDENTIFIER ::= { ciscoProducts 765 }
ciscoASA5550sy  OBJECT IDENTIFIER ::= { ciscoProducts 766 }
ciscoWsSvcFwm1sy OBJECT IDENTIFIER ::= { ciscoProducts 767 }
ciscoPIXFirewall515sy OBJECT IDENTIFIER ::= { ciscoProducts 768 }
ciscoPIXFirewall515Esy OBJECT IDENTIFIER ::= { ciscoProducts 769 }
ciscoPIXFirewall525sy OBJECT IDENTIFIER ::= { ciscoProducts 770 }
ciscoPIXFirewall535sy OBJECT IDENTIFIER ::= { ciscoProducts 771 }
ciscoIpRanOpt4p OBJECT IDENTIFIER ::= { ciscoProducts 772 }
ciscoASA5510sc  OBJECT IDENTIFIER ::= { ciscoProducts 773 }
ciscoASA5510sy  OBJECT IDENTIFIER ::= { ciscoProducts 774 }
ciscoOe512K9    OBJECT IDENTIFIER ::= { ciscoProducts 776 }
ciscoOe612K9    OBJECT IDENTIFIER ::= { ciscoProducts 777 }
catalyst3750G24WS25 OBJECT IDENTIFIER ::= { ciscoProducts 778 }
catalyst3750G24WS50 OBJECT IDENTIFIER ::= { ciscoProducts 779 }
ciscoMe3400g12CsA OBJECT IDENTIFIER ::= { ciscoProducts 780 }
ciscoMe3400g12CsD OBJECT IDENTIFIER ::= { ciscoProducts 781 }
cisco877M       OBJECT IDENTIFIER ::= { ciscoProducts 782 }
cisco1801M      OBJECT IDENTIFIER ::= { ciscoProducts 783 }
catalystWsCBS3040FSC OBJECT IDENTIFIER ::= { ciscoProducts 784 }
ciscoOe511K9    OBJECT IDENTIFIER ::= { ciscoProducts 785 }
ciscoOe611K9    OBJECT IDENTIFIER ::= { ciscoProducts 786 }
ciscoOe7326K9   OBJECT IDENTIFIER ::= { ciscoProducts 787 }
ciscoMe492410GE OBJECT IDENTIFIER ::= { ciscoProducts 788 }
catalyst3750E24TD OBJECT IDENTIFIER ::= { ciscoProducts 789 }
catalyst3750E48TD OBJECT IDENTIFIER ::= { ciscoProducts 790 }
catalyst3750E48PD OBJECT IDENTIFIER ::= { ciscoProducts 791 }
catalyst3750E24PD OBJECT IDENTIFIER ::= { ciscoProducts 792 }
catalyst3560E24TD OBJECT IDENTIFIER ::= { ciscoProducts 793 }
catalyst3560E48TD OBJECT IDENTIFIER ::= { ciscoProducts 794 }
catalyst3560E24PD OBJECT IDENTIFIER ::= { ciscoProducts 795 }
catalyst3560E48PD OBJECT IDENTIFIER ::= { ciscoProducts 796 }
catalyst35608PC OBJECT IDENTIFIER ::= { ciscoProducts 797 }
catalyst29608TC OBJECT IDENTIFIER ::= { ciscoProducts 798 }
catalyst2960G8TC OBJECT IDENTIFIER ::= { ciscoProducts 799 }
ciscoTSPri      OBJECT IDENTIFIER ::= { ciscoProducts 800 }
ciscoTSSec      OBJECT IDENTIFIER ::= { ciscoProducts 801 }
ciscoUWIpPhone7921G OBJECT IDENTIFIER ::= { ciscoProducts 802 }
ciscoUWIpPhone7920 OBJECT IDENTIFIER ::= { ciscoProducts 803 }
cisco3200WirelessMic OBJECT IDENTIFIER ::= { ciscoProducts 804 }
ciscoISRWireless OBJECT IDENTIFIER ::= { ciscoProducts 805 }
ciscoIPSVirtual OBJECT IDENTIFIER ::= { ciscoProducts 806 }
ciscoIDS4215Virtual OBJECT IDENTIFIER ::= { ciscoProducts 807 }
ciscoIDS4235Virtual OBJECT IDENTIFIER ::= { ciscoProducts 808 }
ciscoIDS4250Virtual OBJECT IDENTIFIER ::= { ciscoProducts 809 }
ciscoIDS4250SXVirtual OBJECT IDENTIFIER ::= { ciscoProducts 810 }
ciscoIDS4250XLVirtual OBJECT IDENTIFIER ::= { ciscoProducts 811 }
ciscoIDS4240Virtual OBJECT IDENTIFIER ::= { ciscoProducts 812 }
ciscoIDS4255Virtual OBJECT IDENTIFIER ::= { ciscoProducts 813 }
ciscoIDS4260Virtual OBJECT IDENTIFIER ::= { ciscoProducts 814 }
ciscoIDSIDSM2Virtual OBJECT IDENTIFIER ::= { ciscoProducts 815 }
ciscoIPSSSM20Virtual OBJECT IDENTIFIER ::= { ciscoProducts 816 }
ciscoIPSSSM10Virtual OBJECT IDENTIFIER ::= { ciscoProducts 817 }
ciscoNMWLCE     OBJECT IDENTIFIER ::= { ciscoProducts 818 }
cisco3205WirelessMic OBJECT IDENTIFIER ::= { ciscoProducts 819 }
cisco5720       OBJECT IDENTIFIER ::= { ciscoProducts 820 }
cisco7201       OBJECT IDENTIFIER ::= { ciscoProducts 821 }
ciscoCrs14S     OBJECT IDENTIFIER ::= { ciscoProducts 822 }
ciscoNmWae      OBJECT IDENTIFIER ::= { ciscoProducts 823 }
ciscoACE4710K9  OBJECT IDENTIFIER ::= { ciscoProducts 824 }
ciscoMe3400g2csA OBJECT IDENTIFIER ::= { ciscoProducts 825 }
ciscoNmeNam     OBJECT IDENTIFIER ::= { ciscoProducts 826 }
ciscoUbr7225Vxr OBJECT IDENTIFIER ::= { ciscoProducts 827 }
ciscoAirWlc2106K9 OBJECT IDENTIFIER ::= { ciscoProducts 828 }
ciscoIPS4270    OBJECT IDENTIFIER ::= { ciscoProducts 830 }
ciscoIPS4270Virtual OBJECT IDENTIFIER ::= { ciscoProducts 831 }
ciscoWSC6509ve  OBJECT IDENTIFIER ::= { ciscoProducts 832 }
cisco5740       OBJECT IDENTIFIER ::= { ciscoProducts 833 }
cisco861        OBJECT IDENTIFIER ::= { ciscoProducts 834 }
cisco867        OBJECT IDENTIFIER ::= { ciscoProducts 836 }
cisco881        OBJECT IDENTIFIER ::= { ciscoProducts 837 }
cisco881G       OBJECT IDENTIFIER ::= { ciscoProducts 838 }
ciscoIad881F    OBJECT IDENTIFIER ::= { ciscoProducts 839 }
cisco881Srst    OBJECT IDENTIFIER ::= { ciscoProducts 840 }
ciscoIad881B    OBJECT IDENTIFIER ::= { ciscoProducts 841 }
cisco886        OBJECT IDENTIFIER ::= { ciscoProducts 842 }
cisco886G       OBJECT IDENTIFIER ::= { ciscoProducts 843 }
ciscoIad886F    OBJECT IDENTIFIER ::= { ciscoProducts 844 }
ciscoIad886B    OBJECT IDENTIFIER ::= { ciscoProducts 845 }
cisco886Srst    OBJECT IDENTIFIER ::= { ciscoProducts 846 }
cisco887        OBJECT IDENTIFIER ::= { ciscoProducts 847 }
cisco887G       OBJECT IDENTIFIER ::= { ciscoProducts 848 }
ciscoIad887F    OBJECT IDENTIFIER ::= { ciscoProducts 849 }
ciscoIad887B    OBJECT IDENTIFIER ::= { ciscoProducts 850 }
cisco887Srst    OBJECT IDENTIFIER ::= { ciscoProducts 851 }
cisco888        OBJECT IDENTIFIER ::= { ciscoProducts 852 }
cisco888G       OBJECT IDENTIFIER ::= { ciscoProducts 853 }
ciscoIad888F    OBJECT IDENTIFIER ::= { ciscoProducts 854 }
ciscoIad888B    OBJECT IDENTIFIER ::= { ciscoProducts 855 }
cisco888Srst    OBJECT IDENTIFIER ::= { ciscoProducts 856 }
cisco891        OBJECT IDENTIFIER ::= { ciscoProducts 857 }
cisco892        OBJECT IDENTIFIER ::= { ciscoProducts 858 }
cisco7603s      OBJECT IDENTIFIER ::= { ciscoProducts 862 }
cisco7606s      OBJECT IDENTIFIER ::= { ciscoProducts 863 }
cisco7609s      OBJECT IDENTIFIER ::= { ciscoProducts 864 }
ciscoNMECUE     OBJECT IDENTIFIER ::= { ciscoProducts 866 }
ciscoAIM2CUE    OBJECT IDENTIFIER ::= { ciscoProducts 867 }
ciscoUC500      OBJECT IDENTIFIER ::= { ciscoProducts 868 }
cisco860Ap      OBJECT IDENTIFIER ::= { ciscoProducts 869 }
cisco880Ap      OBJECT IDENTIFIER ::= { ciscoProducts 870 }
cisco890Ap      OBJECT IDENTIFIER ::= { ciscoProducts 871 }
cisco1900Ap     OBJECT IDENTIFIER ::= { ciscoProducts 872 }
cisco340024FSA  OBJECT IDENTIFIER ::= { ciscoProducts 873 }
catalyst4503e   OBJECT IDENTIFIER ::= { ciscoProducts 874 }
catalyst4506e   OBJECT IDENTIFIER ::= { ciscoProducts 875 }
catalyst4507re  OBJECT IDENTIFIER ::= { ciscoProducts 876 }
catalyst4510re  OBJECT IDENTIFIER ::= { ciscoProducts 877 }
ciscoUC520s8U4FXOK9 OBJECT IDENTIFIER ::= { ciscoProducts 878 }
ciscoUC520s8U4FXOWK9 OBJECT IDENTIFIER ::= { ciscoProducts 879 }
ciscoUC520s8U2BRIK9 OBJECT IDENTIFIER ::= { ciscoProducts 880 }
ciscoUC520s8U2BRIWK9 OBJECT IDENTIFIER ::= { ciscoProducts 881 }
ciscoUC520s16U4FXOK9 OBJECT IDENTIFIER ::= { ciscoProducts 882 }
ciscoUC520s16U4FXOWK9 OBJECT IDENTIFIER ::= { ciscoProducts 883 }
ciscoUC520s16U2BRIK9 OBJECT IDENTIFIER ::= { ciscoProducts 884 }
ciscoUC520s16U2BRIWK9 OBJECT IDENTIFIER ::= { ciscoProducts 885 }
ciscoUC520m32U8FXOK9 OBJECT IDENTIFIER ::= { ciscoProducts 886 }
ciscoUC520m32U8FXOWK9 OBJECT IDENTIFIER ::= { ciscoProducts 887 }
ciscoUC520m32U4BRIK9 OBJECT IDENTIFIER ::= { ciscoProducts 888 }
ciscoUC520m32U4BRIWK9 OBJECT IDENTIFIER ::= { ciscoProducts 889 }
ciscoUC520m48U12FXOK9 OBJECT IDENTIFIER ::= { ciscoProducts 890 }
ciscoUC520m48U12FXOWK9 OBJECT IDENTIFIER ::= { ciscoProducts 891 }
ciscoUC520m48U6BRIK9 OBJECT IDENTIFIER ::= { ciscoProducts 892 }
ciscoUC520m48U6BRIWK9 OBJECT IDENTIFIER ::= { ciscoProducts 893 }
ciscoUC520m48U1T1E1FK9 OBJECT IDENTIFIER ::= { ciscoProducts 894 }
ciscoUC520m48U1T1E1BK9 OBJECT IDENTIFIER ::= { ciscoProducts 895 }
catalyst65xxVirtualSwitch OBJECT IDENTIFIER ::= { ciscoProducts 896 }
catalystExpress5208PC OBJECT IDENTIFIER ::= { ciscoProducts 897 }
ciscoMCS7816I   OBJECT IDENTIFIER ::= { ciscoProducts 898 }
ciscoMCS7828I   OBJECT IDENTIFIER ::= { ciscoProducts 899 }
ciscoMCS7816H   OBJECT IDENTIFIER ::= { ciscoProducts 900 }
ciscoMCS7828H   OBJECT IDENTIFIER ::= { ciscoProducts 901 }
cisco1861Uc2BK9 OBJECT IDENTIFIER ::= { ciscoProducts 902 }
cisco1861Uc4FK9 OBJECT IDENTIFIER ::= { ciscoProducts 903 }
cisco1861Srst2BK9 OBJECT IDENTIFIER ::= { ciscoProducts 904 }
cisco1861Srst4FK9 OBJECT IDENTIFIER ::= { ciscoProducts 905 }
ciscoNmeApa     OBJECT IDENTIFIER ::= { ciscoProducts 906 }
ciscoOe7330K9   OBJECT IDENTIFIER ::= { ciscoProducts 907 }
ciscoOe7350K9   OBJECT IDENTIFIER ::= { ciscoProducts 908 }
ciscoSce8000    OBJECT IDENTIFIER ::= { ciscoProducts 913 }
ciscoASA5580    OBJECT IDENTIFIER ::= { ciscoProducts 914 }
ciscoASA5580sc  OBJECT IDENTIFIER ::= { ciscoProducts 915 }
ciscoASA5580sy  OBJECT IDENTIFIER ::= { ciscoProducts 916 }
cat4900M        OBJECT IDENTIFIER ::= { ciscoProducts 917 }
catWsCbs3032Del OBJECT IDENTIFIER ::= { ciscoProducts 920 }
ciscoASR1002    OBJECT IDENTIFIER ::= { ciscoProducts 923 }
ciscoASR1004    OBJECT IDENTIFIER ::= { ciscoProducts 924 }
ciscoASR1006    OBJECT IDENTIFIER ::= { ciscoProducts 925 }
cisco520WirelessController OBJECT IDENTIFIER ::= { ciscoProducts 926 }
cat296048TCS    OBJECT IDENTIFIER ::= { ciscoProducts 927 }
cat296024TCS    OBJECT IDENTIFIER ::= { ciscoProducts 928 }
cat296024S      OBJECT IDENTIFIER ::= { ciscoProducts 929 }
cat3560e12d     OBJECT IDENTIFIER ::= { ciscoProducts 930 }
ciscoCatRfgw    OBJECT IDENTIFIER ::= { ciscoProducts 931 }
catExpress52024TT OBJECT IDENTIFIER ::= { ciscoProducts 932 }
catExpress52024LC OBJECT IDENTIFIER ::= { ciscoProducts 933 }
catExpress52024PC OBJECT IDENTIFIER ::= { ciscoProducts 934 }
catExpress520G24TC OBJECT IDENTIFIER ::= { ciscoProducts 935 }
ciscoCDScde100  OBJECT IDENTIFIER ::= { ciscoProducts 936 }
ciscoCDScde200  OBJECT IDENTIFIER ::= { ciscoProducts 937 }
ciscoCDScde300  OBJECT IDENTIFIER ::= { ciscoProducts 938 }
cisco1861SrstCue2BK9 OBJECT IDENTIFIER ::= { ciscoProducts 939 }
cisco1861SrstCue4FK9 OBJECT IDENTIFIER ::= { ciscoProducts 940 }
ciscoVFrameDataCenter OBJECT IDENTIFIER ::= { ciscoProducts 941 }
ciscoVQEServer  OBJECT IDENTIFIER ::= { ciscoProducts 942 }
ciscoIPSSSM40Virtual OBJECT IDENTIFIER ::= { ciscoProducts 943 }
ciscoIPSSSM40   OBJECT IDENTIFIER ::= { ciscoProducts 944 }
ciscoVgd1t3     OBJECT IDENTIFIER ::= { ciscoProducts 945 }
catalyst296024PC OBJECT IDENTIFIER ::= { ciscoProducts 950 }
catalyst296024LT OBJECT IDENTIFIER ::= { ciscoProducts 951 }
catalyst2960PD8TT OBJECT IDENTIFIER ::= { ciscoProducts 952 }
ciscoN5kC5020pBa OBJECT IDENTIFIER ::= { ciscoProducts 954 }
ciscoN5kC5020pBd OBJECT IDENTIFIER ::= { ciscoProducts 955 }
catalyst3560E12SD OBJECT IDENTIFIER ::= { ciscoProducts 956 }
ciscoOe674      OBJECT IDENTIFIER ::= { ciscoProducts 957 }
ciscoIE30004TC  OBJECT IDENTIFIER ::= { ciscoProducts 958 }
ciscoIE30008TC  OBJECT IDENTIFIER ::= { ciscoProducts 959 }
ciscoRAIE1783MS06T OBJECT IDENTIFIER ::= { ciscoProducts 960 }
ciscoRAIE1783MS10T OBJECT IDENTIFIER ::= { ciscoProducts 961 }
cisco2435Iad8fxs OBJECT IDENTIFIER ::= { ciscoProducts 962 }
ciscoVG204      OBJECT IDENTIFIER ::= { ciscoProducts 963 }
ciscoVG202      OBJECT IDENTIFIER ::= { ciscoProducts 964 }
catalyst291824TT OBJECT IDENTIFIER ::= { ciscoProducts 965 }
catalyst291824TC OBJECT IDENTIFIER ::= { ciscoProducts 966 }
catalyst291848TT OBJECT IDENTIFIER ::= { ciscoProducts 967 }
catalyst291848TC OBJECT IDENTIFIER ::= { ciscoProducts 968 }
ciscoVQETools   OBJECT IDENTIFIER ::= { ciscoProducts 969 }
ciscoUC520m24U4BRIK9 OBJECT IDENTIFIER ::= { ciscoProducts 970 }
ciscoUC520m24U8FXOK9 OBJECT IDENTIFIER ::= { ciscoProducts 971 }
ciscoUC520s16U2BRIWK9J OBJECT IDENTIFIER ::= { ciscoProducts 972 }
ciscoUC520s8U2BRIWK9J OBJECT IDENTIFIER ::= { ciscoProducts 973 }
ciscoVSIntSp    OBJECT IDENTIFIER ::= { ciscoProducts 974 }
ciscoVSSP       OBJECT IDENTIFIER ::= { ciscoProducts 975 }
ciscoVSHydecoder OBJECT IDENTIFIER ::= { ciscoProducts 976 }
ciscoVSDecoder  OBJECT IDENTIFIER ::= { ciscoProducts 977 }
ciscoVSEncoder4P OBJECT IDENTIFIER ::= { ciscoProducts 978 }
ciscoVSEncoder1P OBJECT IDENTIFIER ::= { ciscoProducts 979 }
ciscoSCS1000K9  OBJECT IDENTIFIER ::= { ciscoProducts 980 }
cisco1805       OBJECT IDENTIFIER ::= { ciscoProducts 981 }
ciscoCe7341     OBJECT IDENTIFIER ::= { ciscoProducts 982 }
ciscoCe7371     OBJECT IDENTIFIER ::= { ciscoProducts 983 }
ciscoOe574      OBJECT IDENTIFIER ::= { ciscoProducts 985 }
ciscoOe474      OBJECT IDENTIFIER ::= { ciscoProducts 986 }
ciscoOe274      OBJECT IDENTIFIER ::= { ciscoProducts 987 }
ciscoAp801agn   OBJECT IDENTIFIER ::= { ciscoProducts 988 }
ciscoAp801gn    OBJECT IDENTIFIER ::= { ciscoProducts 989 }
cisco1861WSrstCue4FK9 OBJECT IDENTIFIER ::= { ciscoProducts 990 }
cisco1861WSrstCue2BK9 OBJECT IDENTIFIER ::= { ciscoProducts 991 }
cisco1861WSrst4FK9 OBJECT IDENTIFIER ::= { ciscoProducts 992 }
cisco1861WSrst2BK9 OBJECT IDENTIFIER ::= { ciscoProducts 993 }
cisco1861WUc4FK9 OBJECT IDENTIFIER ::= { ciscoProducts 994 }
cisco1861WUc2BK9 OBJECT IDENTIFIER ::= { ciscoProducts 995 }
ciscoCe674      OBJECT IDENTIFIER ::= { ciscoProducts 996 }
ciscoVQEIST     OBJECT IDENTIFIER ::= { ciscoProducts 997 }
ciscoTSPriG2    OBJECT IDENTIFIER ::= { ciscoProducts 1003 }
catalyst492810GE OBJECT IDENTIFIER ::= { ciscoProducts 1004 }
catalyst296048TTS OBJECT IDENTIFIER ::= { ciscoProducts 1005 }
catalyst29608TCS OBJECT IDENTIFIER ::= { ciscoProducts 1006 }
ciscoMe3400eg2csA OBJECT IDENTIFIER ::= { ciscoProducts 1007 }
ciscoMe3400eg12csM OBJECT IDENTIFIER ::= { ciscoProducts 1008 }
ciscoMe3400e24tsM OBJECT IDENTIFIER ::= { ciscoProducts 1009 }
ciscoIPSSSC5Virtual OBJECT IDENTIFIER ::= { ciscoProducts 1010 }
ciscoSR520FE    OBJECT IDENTIFIER ::= { ciscoProducts 1011 }
ciscoSR520ADSL  OBJECT IDENTIFIER ::= { ciscoProducts 1012 }
ciscoSR520ADSLi OBJECT IDENTIFIER ::= { ciscoProducts 1013 }
ciscoMwr2941DC  OBJECT IDENTIFIER ::= { ciscoProducts 1014 }
catalyst356012PCS OBJECT IDENTIFIER ::= { ciscoProducts 1015 }
catalyst296048PSTL OBJECT IDENTIFIER ::= { ciscoProducts 1016 }
ciscoASR9010    OBJECT IDENTIFIER ::= { ciscoProducts 1017 }
ciscoASR9006    OBJECT IDENTIFIER ::= { ciscoProducts 1018 }
catalyst3560v224tsD OBJECT IDENTIFIER ::= { ciscoProducts 1019 }
catalyst3560v224ts OBJECT IDENTIFIER ::= { ciscoProducts 1020 }
catalyst3560v224ps OBJECT IDENTIFIER ::= { ciscoProducts 1021 }
catalyst3750v224ts OBJECT IDENTIFIER ::= { ciscoProducts 1022 }
catalyst3750v224ps OBJECT IDENTIFIER ::= { ciscoProducts 1023 }
catalyst3560v248ts OBJECT IDENTIFIER ::= { ciscoProducts 1024 }
catalyst3560v248ps OBJECT IDENTIFIER ::= { ciscoProducts 1025 }
catalyst3750v248ts OBJECT IDENTIFIER ::= { ciscoProducts 1026 }
catalyst3750v248ps OBJECT IDENTIFIER ::= { ciscoProducts 1027 }
ciscoHwicCableD2 OBJECT IDENTIFIER ::= { ciscoProducts 1028 }
ciscoHwicCableEJ2 OBJECT IDENTIFIER ::= { ciscoProducts 1029 }
ciscoBr1430     OBJECT IDENTIFIER ::= { ciscoProducts 1030 }
ciscoAIRBR1430  OBJECT IDENTIFIER ::= { ciscoProducts 1031 }
ciscoNamApp2204 OBJECT IDENTIFIER ::= { ciscoProducts 1032 }
ciscoNamApp2220 OBJECT IDENTIFIER ::= { ciscoProducts 1033 }
ciscoAIRAP1141  OBJECT IDENTIFIER ::= { ciscoProducts 1034 }
ciscoAIRAP1142  OBJECT IDENTIFIER ::= { ciscoProducts 1035 }
ciscoASR14K4S   OBJECT IDENTIFIER ::= { ciscoProducts 1036 }
ciscoASR14K8S   OBJECT IDENTIFIER ::= { ciscoProducts 1037 }
cisco18xxx      OBJECT IDENTIFIER ::= { ciscoProducts 1038 }
ciscoIPSSSC5    OBJECT IDENTIFIER ::= { ciscoProducts 1039 }
cisco887Vdsl2   OBJECT IDENTIFIER ::= { ciscoProducts 1040 }
cisco3945       OBJECT IDENTIFIER ::= { ciscoProducts 1041 }
cisco3925       OBJECT IDENTIFIER ::= { ciscoProducts 1042 }
cisco2951       OBJECT IDENTIFIER ::= { ciscoProducts 1043 }
cisco2921       OBJECT IDENTIFIER ::= { ciscoProducts 1044 }
cisco2911       OBJECT IDENTIFIER ::= { ciscoProducts 1045 }
cisco2901       OBJECT IDENTIFIER ::= { ciscoProducts 1046 }
cisco1941       OBJECT IDENTIFIER ::= { ciscoProducts 1047 }
ciscoSm2k15Es1GePoe OBJECT IDENTIFIER ::= { ciscoProducts 1048 }
ciscoSm3k15Es1GePoe OBJECT IDENTIFIER ::= { ciscoProducts 1049 }
ciscoSm3k16GePoe OBJECT IDENTIFIER ::= { ciscoProducts 1050 }
ciscoSm2k23Es1Ge OBJECT IDENTIFIER ::= { ciscoProducts 1051 }
ciscoSm2k23Es1GePoe OBJECT IDENTIFIER ::= { ciscoProducts 1052 }
ciscoSm3k23Es1GePoe OBJECT IDENTIFIER ::= { ciscoProducts 1053 }
ciscoSm3k24GePoe OBJECT IDENTIFIER ::= { ciscoProducts 1054 }
ciscoSmXd2k48Es2SFP OBJECT IDENTIFIER ::= { ciscoProducts 1055 }
ciscoSmXd3k48Es2SFPPoe OBJECT IDENTIFIER ::= { ciscoProducts 1056 }
ciscoSmXd3k48Ge2SFPPoe OBJECT IDENTIFIER ::= { ciscoProducts 1057 }
ciscoEsw52024pK9 OBJECT IDENTIFIER ::= { ciscoProducts 1058 }
ciscoEsw54024pK9 OBJECT IDENTIFIER ::= { ciscoProducts 1059 }
ciscoEsw52048pK9 OBJECT IDENTIFIER ::= { ciscoProducts 1060 }
ciscoEsw52024K9 OBJECT IDENTIFIER ::= { ciscoProducts 1061 }
ciscoEsw54024K9 OBJECT IDENTIFIER ::= { ciscoProducts 1062 }
ciscoEsw52048K9 OBJECT IDENTIFIER ::= { ciscoProducts 1063 }
ciscoEsw54048K9 OBJECT IDENTIFIER ::= { ciscoProducts 1064 }
cisco1861       OBJECT IDENTIFIER ::= { ciscoProducts 1065 }
ciscoUC520      OBJECT IDENTIFIER ::= { ciscoProducts 1066 }
cisco5500Wlc    OBJECT IDENTIFIER ::= { ciscoProducts 1069 }
ciscoSR520T1    OBJECT IDENTIFIER ::= { ciscoProducts 1070 }
ciscoPwrC3900Poe OBJECT IDENTIFIER ::= { ciscoProducts 1071 }
ciscoPwrC3900AC OBJECT IDENTIFIER ::= { ciscoProducts 1072 }
ciscoPwrC2921C2951Poe OBJECT IDENTIFIER ::= { ciscoProducts 1073 }
ciscoPwrC2921C2951AC OBJECT IDENTIFIER ::= { ciscoProducts 1074 }
ciscoPwrC2911Poe OBJECT IDENTIFIER ::= { ciscoProducts 1075 }
ciscoPwrC2911AC OBJECT IDENTIFIER ::= { ciscoProducts 1076 }
ciscoPwrC2901Poe OBJECT IDENTIFIER ::= { ciscoProducts 1077 }
ciscoPwrC1941C2901AC OBJECT IDENTIFIER ::= { ciscoProducts 1078 }
ciscoPwrC1941Poe OBJECT IDENTIFIER ::= { ciscoProducts 1079 }
ciscoPwrC3900DC OBJECT IDENTIFIER ::= { ciscoProducts 1080 }
ciscoPwrC2921C2951DC OBJECT IDENTIFIER ::= { ciscoProducts 1081 }
ciscoPwrC2911DC OBJECT IDENTIFIER ::= { ciscoProducts 1082 }
ciscoRpsAdptrC2921C2951 OBJECT IDENTIFIER ::= { ciscoProducts 1083 }
ciscoRpsAdptrC2911 OBJECT IDENTIFIER ::= { ciscoProducts 1084 }
ciscoCBS3140Stack OBJECT IDENTIFIER ::= { ciscoProducts 1093 }
ciscoCBS3150Stack OBJECT IDENTIFIER ::= { ciscoProducts 1094 }
cisco1941W      OBJECT IDENTIFIER ::= { ciscoProducts 1095 }
ciscoC888E      OBJECT IDENTIFIER ::= { ciscoProducts 1096 }
ciscoC888EG     OBJECT IDENTIFIER ::= { ciscoProducts 1097 }
ciscoIad888EB   OBJECT IDENTIFIER ::= { ciscoProducts 1098 }
ciscoIad888EF   OBJECT IDENTIFIER ::= { ciscoProducts 1099 }
ciscoC888ESRST  OBJECT IDENTIFIER ::= { ciscoProducts 1100 }
cisco3845nv     OBJECT IDENTIFIER ::= { ciscoProducts 1102 }
cisco3825nv     OBJECT IDENTIFIER ::= { ciscoProducts 1103 }
catalystWSC235048TD OBJECT IDENTIFIER ::= { ciscoProducts 1104 }
cisco887M       OBJECT IDENTIFIER ::= { ciscoProducts 1105 }
ciscoCeVirtualBlade OBJECT IDENTIFIER ::= { ciscoProducts 1112 }
ciscoCDScde420  OBJECT IDENTIFIER ::= { ciscoProducts 1113 }
ciscoCDScde220  OBJECT IDENTIFIER ::= { ciscoProducts 1114 }
ciscoCDScde110  OBJECT IDENTIFIER ::= { ciscoProducts 1115 }
ciscoASR1002F   OBJECT IDENTIFIER ::= { ciscoProducts 1116 }
ciscoSecureAccessControlSystem OBJECT IDENTIFIER ::= { ciscoProducts 1117 }
ciscoAIRAP3501  OBJECT IDENTIFIER ::= { ciscoProducts 1124 }
ciscoAIRAP3502  OBJECT IDENTIFIER ::= { ciscoProducts 1125 }
ciscoCDScde400  OBJECT IDENTIFIER ::= { ciscoProducts 1126 }
ciscoSps2004B   OBJECT IDENTIFIER ::= { ciscoProducts 1130 }
ciscoSps204B    OBJECT IDENTIFIER ::= { ciscoProducts 1131 }
ciscoAp541nAK9  OBJECT IDENTIFIER ::= { ciscoProducts 1135 }
ciscoAp541nEK9  OBJECT IDENTIFIER ::= { ciscoProducts 1136 }
ciscoAp541nNK9  OBJECT IDENTIFIER ::= { ciscoProducts 1137 }
cisco887GVdsl2  OBJECT IDENTIFIER ::= { ciscoProducts 1138 }
cisco887SrstVdsl2 OBJECT IDENTIFIER ::= { ciscoProducts 1139 }
cisco3925SPE200 OBJECT IDENTIFIER ::= { ciscoProducts 1144 }
cisco3945SPE250 OBJECT IDENTIFIER ::= { ciscoProducts 1145 }
catalyst296024LCS OBJECT IDENTIFIER ::= { ciscoProducts 1146 }
catalyst296024PCS OBJECT IDENTIFIER ::= { ciscoProducts 1147 }
catalyst296048PSTS OBJECT IDENTIFIER ::= { ciscoProducts 1148 }
ciscoISM        OBJECT IDENTIFIER ::= { ciscoProducts 1149 }
ciscoSM         OBJECT IDENTIFIER ::= { ciscoProducts 1150 }
ciscoNMEAXP     OBJECT IDENTIFIER ::= { ciscoProducts 1151 }
ciscoAIMAXP     OBJECT IDENTIFIER ::= { ciscoProducts 1152 }
ciscoAIM2AXP    OBJECT IDENTIFIER ::= { ciscoProducts 1153 }
ciscoSRP521     OBJECT IDENTIFIER ::= { ciscoProducts 1154 }
ciscoSRP526     OBJECT IDENTIFIER ::= { ciscoProducts 1155 }
ciscoSRP527     OBJECT IDENTIFIER ::= { ciscoProducts 1156 }
ciscoSRP541     OBJECT IDENTIFIER ::= { ciscoProducts 1157 }
ciscoSRP546     OBJECT IDENTIFIER ::= { ciscoProducts 1158 }
ciscoSRP547     OBJECT IDENTIFIER ::= { ciscoProducts 1159 }
ciscoVS510FXO   OBJECT IDENTIFIER ::= { ciscoProducts 1160 }
ciscoNmWae900   OBJECT IDENTIFIER ::= { ciscoProducts 1161 }
ciscoNmWae700   OBJECT IDENTIFIER ::= { ciscoProducts 1162 }
cisco5940RA     OBJECT IDENTIFIER ::= { ciscoProducts 1163 }
cisco5940RC     OBJECT IDENTIFIER ::= { ciscoProducts 1164 }
ciscoASR1001    OBJECT IDENTIFIER ::= { ciscoProducts 1165 }
ciscoASR1013    OBJECT IDENTIFIER ::= { ciscoProducts 1166 }
ciscoCDScde205  OBJECT IDENTIFIER ::= { ciscoProducts 1167 }
ciscoPwr1941AC  OBJECT IDENTIFIER ::= { ciscoProducts 1168 }
ciscoNamWaasVirtualBlade OBJECT IDENTIFIER ::= { ciscoProducts 1169 }
ciscoRaie1783Rms06t OBJECT IDENTIFIER ::= { ciscoProducts 1170 }
ciscoRaie1783Rms10t OBJECT IDENTIFIER ::= { ciscoProducts 1171 }
cisco1941WEK9   OBJECT IDENTIFIER ::= { ciscoProducts 1172 }
cisco1941WPK9   OBJECT IDENTIFIER ::= { ciscoProducts 1173 }
cisco1941WNK9   OBJECT IDENTIFIER ::= { ciscoProducts 1174 }
ciscoMXE5600    OBJECT IDENTIFIER ::= { ciscoProducts 1175 }
ciscoEsw5408pK9 OBJECT IDENTIFIER ::= { ciscoProducts 1176 }
ciscoEsw5208pK9 OBJECT IDENTIFIER ::= { ciscoProducts 1177 }
catalyst4948e10GE OBJECT IDENTIFIER ::= { ciscoProducts 1178 }
cisco1921k9     OBJECT IDENTIFIER ::= { ciscoProducts 1191 }
ciscoASA5585Ssp10 OBJECT IDENTIFIER ::= { ciscoProducts 1194 }
ciscoASA5585Ssp20 OBJECT IDENTIFIER ::= { ciscoProducts 1195 }
ciscoASA5585Ssp40 OBJECT IDENTIFIER ::= { ciscoProducts 1196 }
ciscoASA5585Ssp60 OBJECT IDENTIFIER ::= { ciscoProducts 1197 }
ciscoASA5585Ssp10sc OBJECT IDENTIFIER ::= { ciscoProducts 1198 }
ciscoASA5585Ssp20sc OBJECT IDENTIFIER ::= { ciscoProducts 1199 }
ciscoASA5585Ssp40sc OBJECT IDENTIFIER ::= { ciscoProducts 1200 }
ciscoASA5585Ssp60sc OBJECT IDENTIFIER ::= { ciscoProducts 1201 }
ciscoASA5585Ssp10sy OBJECT IDENTIFIER ::= { ciscoProducts 1202 }
ciscoASA5585Ssp20sy OBJECT IDENTIFIER ::= { ciscoProducts 1203 }
ciscoASA5585Ssp40sy OBJECT IDENTIFIER ::= { ciscoProducts 1204 }
ciscoASA5585Ssp60sy OBJECT IDENTIFIER ::= { ciscoProducts 1205 }
ciscoOeNm302    OBJECT IDENTIFIER ::= { ciscoProducts 1209 }
ciscoOeNm502    OBJECT IDENTIFIER ::= { ciscoProducts 1210 }
ciscoOeNm522    OBJECT IDENTIFIER ::= { ciscoProducts 1211 }
ciscoOeSmSre700 OBJECT IDENTIFIER ::= { ciscoProducts 1212 }
ciscoOeSmSre900 OBJECT IDENTIFIER ::= { ciscoProducts 1213 }
ciscoVsaNam     OBJECT IDENTIFIER ::= { ciscoProducts 1214 }
ciscoMwr2941DCA OBJECT IDENTIFIER ::= { ciscoProducts 1215 }
cisco1941WCK9   OBJECT IDENTIFIER ::= { ciscoProducts 1220 }
ciscoCDScde2202s3 OBJECT IDENTIFIER ::= { ciscoProducts 1221 }
ciscoNMEAIR     OBJECT IDENTIFIER ::= { ciscoProducts 1230 }
ciscoACE30K9    OBJECT IDENTIFIER ::= { ciscoProducts 1231 }
ciscoASA5585SspIps10 OBJECT IDENTIFIER ::= { ciscoProducts 1232 }
ciscoASA5585SspIps20 OBJECT IDENTIFIER ::= { ciscoProducts 1233 }
ciscoASA5585SspIps40 OBJECT IDENTIFIER ::= { ciscoProducts 1234 }
ciscoASA5585SspIps60 OBJECT IDENTIFIER ::= { ciscoProducts 1235 }
cisco1841CK9    OBJECT IDENTIFIER ::= { ciscoProducts 1236 }
cisco2801CK9    OBJECT IDENTIFIER ::= { ciscoProducts 1237 }
cisco2811CK9    OBJECT IDENTIFIER ::= { ciscoProducts 1238 }
cisco2821CK9    OBJECT IDENTIFIER ::= { ciscoProducts 1239 }
cisco3825CK9    OBJECT IDENTIFIER ::= { ciscoProducts 1241 }
cisco3845CK9    OBJECT IDENTIFIER ::= { ciscoProducts 1242 }
ciscoCGS252024TC OBJECT IDENTIFIER ::= { ciscoProducts 1245 }
ciscoCGS252016S8PC OBJECT IDENTIFIER ::= { ciscoProducts 1246 }
ciscoAIRAP1262  OBJECT IDENTIFIER ::= { ciscoProducts 1247 }
ciscoAIRAP1261  OBJECT IDENTIFIER ::= { ciscoProducts 1248 }
cisco892F       OBJECT IDENTIFIER ::= { ciscoProducts 1249 }
ciscoCGR2010    OBJECT IDENTIFIER ::= { ciscoProducts 1253 }
ciscoPwrCGR20xxCGS25xxPoeAC OBJECT IDENTIFIER ::= { ciscoProducts 1254 }
ciscoPwrCGR20xxCGS25xxPoeDC OBJECT IDENTIFIER ::= { ciscoProducts 1255 }
catWsC2960s48tsS OBJECT IDENTIFIER ::= { ciscoProducts 1256 }
catWsC2960s24tsS OBJECT IDENTIFIER ::= { ciscoProducts 1257 }
catWsC2960s48fpdL OBJECT IDENTIFIER ::= { ciscoProducts 1258 }
catWsC2960s48ldpL OBJECT IDENTIFIER ::= { ciscoProducts 1259 }
catWsC2960s48tdL OBJECT IDENTIFIER ::= { ciscoProducts 1260 }
catWsC2960s24pdL OBJECT IDENTIFIER ::= { ciscoProducts 1261 }
catWsC2960s24tdL OBJECT IDENTIFIER ::= { ciscoProducts 1262 }
catWsC2960s48fpsL OBJECT IDENTIFIER ::= { ciscoProducts 1263 }
catWsC2960s48lpsL OBJECT IDENTIFIER ::= { ciscoProducts 1264 }
catWsC2960s24psL OBJECT IDENTIFIER ::= { ciscoProducts 1265 }
catWsC2960s48tsL OBJECT IDENTIFIER ::= { ciscoProducts 1266 }
catWsC2960s24tsL OBJECT IDENTIFIER ::= { ciscoProducts 1267 }
cisco1906CK9    OBJECT IDENTIFIER ::= { ciscoProducts 1268 }
ciscoAIRAP1042  OBJECT IDENTIFIER ::= { ciscoProducts 1269 }
ciscoAIRAP1041  OBJECT IDENTIFIER ::= { ciscoProducts 1270 }
ciscoASASm1sc   OBJECT IDENTIFIER ::= { ciscoProducts 1275 }
ciscoASASm1sy   OBJECT IDENTIFIER ::= { ciscoProducts 1276 }
ciscoASASm1     OBJECT IDENTIFIER ::= { ciscoProducts 1277 }
cat2960cPD8TT   OBJECT IDENTIFIER ::= { ciscoProducts 1278 }
ciscoAirCt2504K9 OBJECT IDENTIFIER ::= { ciscoProducts 1279 }
ciscoISMAXP     OBJECT IDENTIFIER ::= { ciscoProducts 1280 }
ciscoSMAXP      OBJECT IDENTIFIER ::= { ciscoProducts 1281 }
ciscoAxpSmSre900 OBJECT IDENTIFIER ::= { ciscoProducts 1282 }
ciscoAxpSmSre700 OBJECT IDENTIFIER ::= { ciscoProducts 1283 }
ciscoAxpIsmSre300 OBJECT IDENTIFIER ::= { ciscoProducts 1284 }
ciscoCDSISM     OBJECT IDENTIFIER ::= { ciscoProducts 1285 }
ciscoAxpNme302  OBJECT IDENTIFIER ::= { ciscoProducts 1288 }
ciscoAxpNme502  OBJECT IDENTIFIER ::= { ciscoProducts 1289 }
ciscoAxpNme522  OBJECT IDENTIFIER ::= { ciscoProducts 1290 }
ciscoACE20K9    OBJECT IDENTIFIER ::= { ciscoProducts 1291 }
ciscoWsC236048tdS OBJECT IDENTIFIER ::= { ciscoProducts 1292 }
ciscoCDScde250  OBJECT IDENTIFIER ::= { ciscoProducts 1294 }
ciscoAnmVirtualApp OBJECT IDENTIFIER ::= { ciscoProducts 1296 }
ciscoECDS3100   OBJECT IDENTIFIER ::= { ciscoProducts 1297 }
ciscoECDS1100   OBJECT IDENTIFIER ::= { ciscoProducts 1298 }
catWsC3750v224fsS OBJECT IDENTIFIER ::= { ciscoProducts 1300 }
ciscoOeVWaas    OBJECT IDENTIFIER ::= { ciscoProducts 1301 }
ciscoASA5585Ssp10K7 OBJECT IDENTIFIER ::= { ciscoProducts 1302 }
ciscoASA5585Ssp20K7 OBJECT IDENTIFIER ::= { ciscoProducts 1303 }
ciscoASA5585Ssp40K7 OBJECT IDENTIFIER ::= { ciscoProducts 1304 }
ciscoASA5585Ssp60K7 OBJECT IDENTIFIER ::= { ciscoProducts 1305 }
ciscoASA5585Ssp10K7sc OBJECT IDENTIFIER ::= { ciscoProducts 1306 }
ciscoASA5585Ssp20K7sc OBJECT IDENTIFIER ::= { ciscoProducts 1307 }
ciscoASA5585Ssp40K7sc OBJECT IDENTIFIER ::= { ciscoProducts 1308 }
ciscoASA5585Ssp60K7sc OBJECT IDENTIFIER ::= { ciscoProducts 1309 }
ciscoASA5585Ssp10K7sy OBJECT IDENTIFIER ::= { ciscoProducts 1310 }
ciscoASA5585Ssp20K7sy OBJECT IDENTIFIER ::= { ciscoProducts 1311 }
ciscoASA5585Ssp40K7sy OBJECT IDENTIFIER ::= { ciscoProducts 1312 }
ciscoASA5585Ssp60K7sy OBJECT IDENTIFIER ::= { ciscoProducts 1313 }
ciscoSreSmNam   OBJECT IDENTIFIER ::= { ciscoProducts 1314 }
ciscoIE301016S8PC OBJECT IDENTIFIER ::= { ciscoProducts 1319 }
ciscoIE301024TC OBJECT IDENTIFIER ::= { ciscoProducts 1320 }
ciscoASA5585SspIps10K7 OBJECT IDENTIFIER ::= { ciscoProducts 1323 }
ciscoASA5585SspIps20K7 OBJECT IDENTIFIER ::= { ciscoProducts 1324 }
ciscoASA5585SspIps40K7 OBJECT IDENTIFIER ::= { ciscoProducts 1325 }
ciscoASA5585SspIps60K7 OBJECT IDENTIFIER ::= { ciscoProducts 1326 }
catalyst4948ef10GE OBJECT IDENTIFIER ::= { ciscoProducts 1327 }
cat292824TCC    OBJECT IDENTIFIER ::= { ciscoProducts 1328 }
cat292848TCC    OBJECT IDENTIFIER ::= { ciscoProducts 1329 }
cat292824LTC    OBJECT IDENTIFIER ::= { ciscoProducts 1330 }
ciscoCrs16SB    OBJECT IDENTIFIER ::= { ciscoProducts 1331 }
ciscoQuad       OBJECT IDENTIFIER ::= { ciscoProducts 1332 }
ciscoASASm1K7sc OBJECT IDENTIFIER ::= { ciscoProducts 1334 }
ciscoASASm1K7sy OBJECT IDENTIFIER ::= { ciscoProducts 1335 }
ciscoASASm1K7   OBJECT IDENTIFIER ::= { ciscoProducts 1336 }
ciscoPwrCGR2010PoeAC OBJECT IDENTIFIER ::= { ciscoProducts 1337 }
ciscoPwrCGR2010PoeDC OBJECT IDENTIFIER ::= { ciscoProducts 1338 }
cisco1861eUc2BK9 OBJECT IDENTIFIER ::= { ciscoProducts 1339 }
cisco1861eUc4FK9 OBJECT IDENTIFIER ::= { ciscoProducts 1340 }
ciscoC1861eSrstFK9 OBJECT IDENTIFIER ::= { ciscoProducts 1341 }
ciscoC1861eSrstBK9 OBJECT IDENTIFIER ::= { ciscoProducts 1342 }
ciscoC1861eSrstCFK9 OBJECT IDENTIFIER ::= { ciscoProducts 1343 }
ciscoC1861eSrstCBK9 OBJECT IDENTIFIER ::= { ciscoProducts 1344 }
ciscoUCVirtualMachine OBJECT IDENTIFIER ::= { ciscoProducts 1348 }
ciscoWave8541   OBJECT IDENTIFIER ::= { ciscoProducts 1349 }
ciscoWave7571   OBJECT IDENTIFIER ::= { ciscoProducts 1350 }
ciscoWave7541   OBJECT IDENTIFIER ::= { ciscoProducts 1351 }
ciscoWave694    OBJECT IDENTIFIER ::= { ciscoProducts 1352 }
ciscoWave594    OBJECT IDENTIFIER ::= { ciscoProducts 1353 }
ciscoWave294    OBJECT IDENTIFIER ::= { ciscoProducts 1354 }
cisco5915RC     OBJECT IDENTIFIER ::= { ciscoProducts 1355 }
cisco5915RA     OBJECT IDENTIFIER ::= { ciscoProducts 1356 }
cisco867VAEK9   OBJECT IDENTIFIER ::= { ciscoProducts 1358 }
cisco866VAEK9   OBJECT IDENTIFIER ::= { ciscoProducts 1359 }
cisco867VAE     OBJECT IDENTIFIER ::= { ciscoProducts 1360 }
cisco866VAE     OBJECT IDENTIFIER ::= { ciscoProducts 1361 }
catwsC2960C8tcS OBJECT IDENTIFIER ::= { ciscoProducts 1364 }
catwsC2960C8tcL OBJECT IDENTIFIER ::= { ciscoProducts 1365 }
catwsC2960C8pcL OBJECT IDENTIFIER ::= { ciscoProducts 1366 }
catwsC2960C12pcL OBJECT IDENTIFIER ::= { ciscoProducts 1367 }
catwsC3560CPD8ptS OBJECT IDENTIFIER ::= { ciscoProducts 1368 }
cisco1841ve     OBJECT IDENTIFIER ::= { ciscoProducts 1369 }
cisco2811ve     OBJECT IDENTIFIER ::= { ciscoProducts 1370 }
cisco881WAK9    OBJECT IDENTIFIER ::= { ciscoProducts 1371 }
cisco881WEK9    OBJECT IDENTIFIER ::= { ciscoProducts 1372 }
cisco881WPK9    OBJECT IDENTIFIER ::= { ciscoProducts 1373 }
cisco886VaWEK9  OBJECT IDENTIFIER ::= { ciscoProducts 1374 }
cisco887VamWEK9 OBJECT IDENTIFIER ::= { ciscoProducts 1375 }
cisco887VaWAK9  OBJECT IDENTIFIER ::= { ciscoProducts 1376 }
cisco887VaWEK9  OBJECT IDENTIFIER ::= { ciscoProducts 1377 }
cisco819GUK9    OBJECT IDENTIFIER ::= { ciscoProducts 1378 }
cisco819GSK9    OBJECT IDENTIFIER ::= { ciscoProducts 1379 }
cisco819GVK9    OBJECT IDENTIFIER ::= { ciscoProducts 1380 }
cisco819GBK9    OBJECT IDENTIFIER ::= { ciscoProducts 1381 }
cisco819G7AK9   OBJECT IDENTIFIER ::= { ciscoProducts 1382 }
cisco819G7K9    OBJECT IDENTIFIER ::= { ciscoProducts 1383 }
cisco819HGUK9   OBJECT IDENTIFIER ::= { ciscoProducts 1384 }
cisco819HGSK9   OBJECT IDENTIFIER ::= { ciscoProducts 1385 }
cisco819HGVK9   OBJECT IDENTIFIER ::= { ciscoProducts 1386 }
cisco819HGBK9   OBJECT IDENTIFIER ::= { ciscoProducts 1387 }
cisco819HG7AK9  OBJECT IDENTIFIER ::= { ciscoProducts 1388 }
cisco819HG7K9   OBJECT IDENTIFIER ::= { ciscoProducts 1389 }
cat3750x24s     OBJECT IDENTIFIER ::= { ciscoProducts 1404 }
cat3750x12s     OBJECT IDENTIFIER ::= { ciscoProducts 1405 }
ciscoNME        OBJECT IDENTIFIER ::= { ciscoProducts 1406 }
ciscoPCM        OBJECT IDENTIFIER ::= { ciscoProducts 1422 }
ciscoIse3315K9  OBJECT IDENTIFIER ::= { ciscoProducts 1423 }
ciscoIse3395K9  OBJECT IDENTIFIER ::= { ciscoProducts 1424 }
ciscoIse3355K9  OBJECT IDENTIFIER ::= { ciscoProducts 1425 }
ciscoIseVmK9    OBJECT IDENTIFIER ::= { ciscoProducts 1426 }
ciscoEcdsVB     OBJECT IDENTIFIER ::= { ciscoProducts 1432 }
ciscoASA5585SspIps10Virtual OBJECT IDENTIFIER ::= { ciscoProducts 1437 }
ciscoASA5585SspIps20Virtual OBJECT IDENTIFIER ::= { ciscoProducts 1438 }
ciscoASA5585SspIps40Virtual OBJECT IDENTIFIER ::= { ciscoProducts 1439 }
ciscoASA5585SspIps60Virtual OBJECT IDENTIFIER ::= { ciscoProducts 1440 }
ciscoASR5500    OBJECT IDENTIFIER ::= { ciscoProducts 1457 }
ciscoXfp10Ger192IrL OBJECT IDENTIFIER ::= { ciscoProducts 1462 }
ciscoXfp10Glr192SrL OBJECT IDENTIFIER ::= { ciscoProducts 1463 }
ciscoXfp10Gzr192LrL OBJECT IDENTIFIER ::= { ciscoProducts 1464 }
catwsC3560C12pcS OBJECT IDENTIFIER ::= { ciscoProducts 1465 }
catwsC3560C8pcS OBJECT IDENTIFIER ::= { ciscoProducts 1466 }
ciscoCRSFabBP   OBJECT IDENTIFIER ::= { ciscoProducts 1467 }
ciscoA9k2X100GeSe OBJECT IDENTIFIER ::= { ciscoProducts 1494 }
ciscoA9k2X100GeTr OBJECT IDENTIFIER ::= { ciscoProducts 1495 }
ciscoA9k24X10GeSe OBJECT IDENTIFIER ::= { ciscoProducts 1496 }
ciscoA9k24X10GeTr OBJECT IDENTIFIER ::= { ciscoProducts 1497 }
ciscoA9kMOD80SE OBJECT IDENTIFIER ::= { ciscoProducts 1498 }
ciscoA9kMOD80TR OBJECT IDENTIFIER ::= { ciscoProducts 1499 }
ciscoA9kMOD160SE OBJECT IDENTIFIER ::= { ciscoProducts 1500 }
ciscoA9kMOD160TR OBJECT IDENTIFIER ::= { ciscoProducts 1501 }
ciscoA9kMPA2X10GE OBJECT IDENTIFIER ::= { ciscoProducts 1502 }
ciscoA9kMPA4X10GE OBJECT IDENTIFIER ::= { ciscoProducts 1503 }
ciscoA9kMPA20X1GE OBJECT IDENTIFIER ::= { ciscoProducts 1504 }
ciscoA9kMPA1X40GE OBJECT IDENTIFIER ::= { ciscoProducts 1505 }
ciscoA9kMPA2X40GE OBJECT IDENTIFIER ::= { ciscoProducts 1506 }
ciscoUcsC200    OBJECT IDENTIFIER ::= { ciscoProducts 1512 }
ciscoUcsC210    OBJECT IDENTIFIER ::= { ciscoProducts 1513 }
ciscoUcsC250    OBJECT IDENTIFIER ::= { ciscoProducts 1514 }
ciscoUcsC260    OBJECT IDENTIFIER ::= { ciscoProducts 1515 }
ciscoUcsC460    OBJECT IDENTIFIER ::= { ciscoProducts 1516 }
ciscoASR901     OBJECT IDENTIFIER ::= { ciscoProducts 1521 }
ciscoASR901E    OBJECT IDENTIFIER ::= { ciscoProducts 1522 }
ciscoNam2304    OBJECT IDENTIFIER ::= { ciscoProducts 1527 }
ciscoNam2320    OBJECT IDENTIFIER ::= { ciscoProducts 1528 }
ciscoNam3       OBJECT IDENTIFIER ::= { ciscoProducts 1529 }
cisco819HG4GAK9 OBJECT IDENTIFIER ::= { ciscoProducts 1530 }
ciscoASR5000    OBJECT IDENTIFIER ::= { ciscoProducts 1538 }
ciscoflowAgent3000 OBJECT IDENTIFIER ::= { ciscoProducts 1539 }


END
